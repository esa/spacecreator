-- DRIVER CONFIGURATION MODEL [user-editable]
-- Shall contain definition of Driver Configuration.
-- This file will be used by ocarina-components.aadl and Board1.xml.
%{ProjectNameUpperCaseEscaped}-DRIVER-CONFIGURATION DEFINITIONS ::= BEGIN

    %{ProjectNameUpperCaseEscaped}-Conf-T ::= SEQUENCE {
        -- Driver Configuration
    }

    -- ASN.1 Type definitions must start with an uppercase
    -- Field names in records (SEQUENCE) must start with a lowercase
    -- Underscores are not allowed: use dash (hyphen)
    -- For integers do not assume that small ranges will be translated to small
    -- types in C or Ada (expect unsigned or signed 64 bits types with subtypes
    -- for the range in Ada)

    -- Simple types:

    -- TASTE-Boolean ::= BOOLEAN
    -- MyInteger ::= INTEGER (0..255)
    -- MyReal ::= REAL (0.0 .. 1000.0)
    -- MyBool ::= BOOLEAN
    -- MyEnum ::= ENUMERATED { hello, world, how-are-you }

    -- Complex types:

    --  MySeq ::= SEQUENCE {
    --      input-data  MyInteger,
    --      output-data MyInteger,
    --      validity    ENUMERATED { valid, invalid }
    -- }
    --
    --  MyChoice ::= CHOICE {
    --      a BOOLEAN,
    --      b MySeq
    -- }
    --
    --  MySeqOf ::= SEQUENCE (SIZE (2)) OF MyEnum
    --
    --  MyOctStr ::= OCTET STRING (SIZE (3))
    --
    --  You can also declare constants
    --  myVar       MySeqOf ::= { hello, world }

END
