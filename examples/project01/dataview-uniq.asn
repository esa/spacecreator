TASTE-BasicTypes DEFINITIONS ::=
BEGIN
T-UInt32 ::= INTEGER (0..4294967295)
TASTE-Peek-id ::= INTEGER (0..4294967295)

T-Boolean ::= BOOLEAN

TASTE-Peek-id-list ::= SEQUENCE (SIZE (1..10)) OF TASTE-Peek-id
FixedIntList ::= SEQUENCE (SIZE(3)) OF TASTE-Peek-id

MyEnum ::= ENUMERATED {one, two, three, four, five}

MyChoice ::= CHOICE { a BOOLEAN, b ENUMERATED { aa, bb } }

MySeq ::= SEQUENCE { a BOOLEAN, b MyChoice }

MySetOf ::= SET (SIZE(1..3)) OF INTEGER (0..10)

MySeqOf ::= SEQUENCE (SIZE(1..3)) OF INTEGER (0..10)

MySimpleSeq ::= SEQUENCE { a INTEGER (0..255), b BOOLEAN, c MyEnum }

END
