TASTE-BasicTypes DEFINITIONS ::=
BEGIN

-- Set of TASTE predefined basic types

T-Int31 ::=  INTEGER (-2147483648 .. 2147483647)

T-UInt31 ::= INTEGER (0 .. 4294967295)

T-Int7 ::= INTEGER (-128 .. 127)

T-UInt7 ::= INTEGER (0 .. 255)

T-Boolean ::= BOOLEAN

T-Real ::= REAL (-1.0 .. 1.0)

T-Enum ::= ENUMERATION (Enum_0, Enum_1, Enum_2)

T-String ::= STRING
END
