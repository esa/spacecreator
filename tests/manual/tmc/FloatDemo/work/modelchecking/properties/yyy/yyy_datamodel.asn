Yyy-Datamodel DEFINITIONS ::=
BEGIN
--  This file was generated automatically by OpenGEODE
IMPORTS
   Actuator-States, Actuator-Context FROM Actuator-Datamodel
   Controlsystem-States, Controlsystem-Context FROM Controlsystem-Datamodel
   Demo-timer-manager-States, Demo-timer-manager-Context FROM Demo-timer-manager-Datamodel
   Host-States, Host-Context FROM Host-Datamodel
   Sensor-States, Sensor-Context FROM Sensor-Datamodel
   INumber, IPidConfig, Number, PidConfig FROM FLOATDEMO-DATAVIEW
   T-Int32, T-UInt32, T-Int8, T-UInt8, T-Boolean, T-Null-Record FROM TASTE-BasicTypes
   PID-Range, PID FROM System-Dataview
   Actuator-Event, Controlsystem-Event, Demo-Timer-Manager-Event, Demo-Timer-Manager-Periodic-Events, Host-Event, Sensor-Event, Observer-State-Kind, Function-Event, Named-Function-Event, Interface-Event, Observable-Event, Events-Ty, System-State FROM Simulation-DataView
   TimerData, AggregateTimerData FROM Simulation-Timers-DataView;

Yyy-States ::= ENUMERATED {error}

Yyy-Context ::= SEQUENCE {
   state Yyy-States,
   init-done BOOLEAN,
   sender PID
}

Yyy-Actuator-Event-Msg-In-Selection  ::= ENUMERATED {input-none-present(1), controlsignal-present(2)}
Yyy-Actuator-Event-Selection  ::= ENUMERATED {msg-in-present(1)}
Yyy-Sensor-Event-Msg-In-Selection  ::= ENUMERATED {input-none-present(1), tc-present(2), trigger-present(3)}
Yyy-Sensor-Event-Msg-Out-Selection  ::= ENUMERATED {reading-present(1)}
Yyy-Sensor-Event-Selection  ::= ENUMERATED {msg-in-present(1), msg-out-present(2)}
Yyy-Controlsystem-Event-Msg-In-Selection  ::= ENUMERATED {input-none-present(1), configuration-present(2), reading-present(3)}
Yyy-Controlsystem-Event-Msg-Out-Selection  ::= ENUMERATED {controlsignal-present(1), tm-present(2)}
Yyy-Controlsystem-Event-Selection  ::= ENUMERATED {msg-in-present(1), msg-out-present(2)}
Yyy-Host-Event-Msg-In-Selection  ::= ENUMERATED {input-none-present(1), tm-present(2)}
Yyy-Host-Event-Msg-Out-Selection  ::= ENUMERATED {configuration-present(1), tc-present(2)}
Yyy-Host-Event-Selection  ::= ENUMERATED {msg-in-present(1), msg-out-present(2)}
Yyy-Demo-Timer-Manager-Event-Msg-In-Selection  ::= ENUMERATED {input-none-present(1), tick-present(2)}
Yyy-Demo-Timer-Manager-Event-Msg-Out-Selection  ::= ENUMERATED {sensor-trigger-present(1)}
Yyy-Demo-Timer-Manager-Event-Selection  ::= ENUMERATED {msg-in-present(1), msg-out-present(2)}
Yyy-Function-Event-Selection  ::= ENUMERATED {actuator-present(1), controlsystem-present(2), env-present(3), host-present(4), sensor-present(5)}
Yyy-Observable-Event-Selection  ::= ENUMERATED {no-event-present(1), system-startup-present(2), input-event-present(3), output-event-present(4), unhandled-input-present(5)}
END
