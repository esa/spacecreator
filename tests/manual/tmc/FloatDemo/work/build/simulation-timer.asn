Simulation-Timers-DataView DEFINITIONS ::=
BEGIN

   TimerData ::= SEQUENCE {
      timer-enabled BOOLEAN,
      interval INTEGER (0 .. 50000)
   }

   AggregateTimerData ::= SEQUENCE {
      
      
      
      actuator SEQUENCE {
      },
      
      controlsystem SEQUENCE {
      },
      
      host SEQUENCE {
      },
      
      sensor SEQUENCE {
         trigger TimerData
      
      },
      
      dummy-entry SEQUENCE {}
   }

END
