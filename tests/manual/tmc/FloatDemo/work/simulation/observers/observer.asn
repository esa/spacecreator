Actuator-Datamodel DEFINITIONS ::=
BEGIN
--  This file was generated automatically by OpenGEODE
IMPORTS
   Number, PidConfig FROM FLOATDEMO-DATAVIEW
   T-Int32, T-UInt32, T-Int8, T-UInt8, T-Boolean, T-Null-Record FROM TASTE-BasicTypes
   PID-Range, PID FROM System-Dataview;

Actuator-States ::= ENUMERATED {idle, activated}

Actuator-Context ::= SEQUENCE {
   state Actuator-States,
   init-done BOOLEAN,
   sender PID,
   setting Number,
   inputcontrol Number
}

END

Controlsystem-Datamodel DEFINITIONS ::=
BEGIN
--  This file was generated automatically by OpenGEODE
IMPORTS
   Number, PidConfig FROM FLOATDEMO-DATAVIEW
   T-Int32, T-UInt32, T-Int8, T-UInt8, T-Boolean, T-Null-Record FROM TASTE-BasicTypes
   PID-Range, PID FROM System-Dataview;

Controlsystem-States ::= ENUMERATED {off, configured}

Controlsystem-Context ::= SEQUENCE {
   state Controlsystem-States,
   init-done BOOLEAN,
   sender PID,
   cfg PidConfig,
   inputvalue Number,
   outputvalue Number,
   i Number,
   d Number,
   previous Number
}

END

Host-Datamodel DEFINITIONS ::=
BEGIN
--  This file was generated automatically by OpenGEODE
IMPORTS
   Number, PidConfig FROM FLOATDEMO-DATAVIEW
   T-Int32, T-UInt32, T-Int8, T-UInt8, T-Boolean, T-Null-Record FROM TASTE-BasicTypes
   PID-Range, PID FROM System-Dataview;

Host-States ::= ENUMERATED {wait}

Host-Context ::= SEQUENCE {
   state Host-States,
   init-done BOOLEAN,
   sender PID,
   cfg PidConfig
}

END

Sensor-Datamodel DEFINITIONS ::=
BEGIN
--  This file was generated automatically by OpenGEODE
IMPORTS
   Number, PidConfig FROM FLOATDEMO-DATAVIEW
   T-Int32, T-UInt32, T-Int8, T-UInt8, T-Boolean, T-Null-Record FROM TASTE-BasicTypes
   PID-Range, PID FROM System-Dataview;

Sensor-States ::= ENUMERATED {wait}

Sensor-Context ::= SEQUENCE {
   state Sensor-States,
   init-done BOOLEAN,
   sender PID,
   x Number
}

END

FLOATDEMO-DATAVIEW DEFINITIONS ::=
BEGIN

   Number ::= REAL (-1000.0 .. 1000.0)

   PidConfig ::= SEQUENCE {
       kp Number,
       ki Number,
       kd Number
   }

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..5)

   -- List of functions (instances) present in the system
   PID ::= ENUMERATED {
       actuator,
       controlsystem,
       dummy,
       host,
       sensor,
       
       env
   }

END


Simulation-DataView DEFINITIONS ::=
BEGIN
   IMPORTS
      
      --  ASN.1 modules used by thread actuator_controlSignal
      Number FROM FLOATDEMO-DATAVIEW
      
      --  ASN.1 modules used by thread controlsystem_configuration
      PidConfig FROM FLOATDEMO-DATAVIEW
      
      --  ASN.1 modules used by thread controlsystem_reading
      Number FROM FLOATDEMO-DATAVIEW
      
      
      
      
      -- Import generic integer type (used for timers)
      T-UInt32 FROM TASTE-BasicTypes
      PID      FROM System-Dataview
      -- Import timers
      AggregateTimerData FROM Simulation-Timers-DataView
      --  Import the SDL function states needed for the global system state
      Actuator-Context      FROM Actuator-Datamodel
      Controlsystem-Context FROM Controlsystem-Datamodel
      Host-Context          FROM Host-Datamodel
      Sensor-Context        FROM Sensor-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Actuator-Event ::= CHOICE {
      msg-in CHOICE {
         input-none SEQUENCE {},
         controlsignal SEQUENCE { controlvalue Number}
      }
   }
   
   Controlsystem-Event ::= CHOICE {
      msg-in CHOICE {
         input-none SEQUENCE {},
         configuration SEQUENCE { cfg PidConfig},
         reading       SEQUENCE { signalvalue Number}
      },
      msg-out CHOICE {
         controlsignal SEQUENCE { controlvalue Number }
      }
   }
   
   Dummy-Event ::= CHOICE {
      msg-out CHOICE {
         dummy SEQUENCE {   }
      }
   }
   
   Host-Event ::= CHOICE {
      msg-in CHOICE {
         input-none SEQUENCE {},
         dummy SEQUENCE {  }
      },
      msg-out CHOICE {
         configuration SEQUENCE { cfg PidConfig }
      }
   }
   
   Sensor-Event ::= CHOICE {
      msg-in CHOICE {
         input-none SEQUENCE {},
         trigger SEQUENCE {  }
      },
      msg-out CHOICE {
         reading SEQUENCE { signalvalue Number }
      }
   }
   Sensor-Periodic-Events ::=
      Periodic-Events {Sensor-Event, 1}
   
   sensor-periodic-events Sensor-Periodic-Events ::= {
      { period 1000, event msg-in: trigger : {} }
   }
   

   --  Current observer state flag (used by model checkers)
   Observer-State-Kind ::= ENUMERATED {
      regular-state,
      error-state,
      ignore-state,
      success-state
   }

   --  Event related to the execution of a PI or call of a RI in the functional code
   Function-Event ::= CHOICE {
      actuator      Actuator-Event,
      controlsystem Controlsystem-Event,
      dummy         Dummy-Event,
      host          Host-Event,
      sensor        Sensor-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   actuator-queue-size INTEGER ::= 2
   controlsystem-queue-size INTEGER ::= 2
   host-queue-size INTEGER ::= 2
   sensor-queue-size INTEGER ::= 2

   System-State ::= SEQUENCE {
      --  Timers
      timers AggregateTimerData,
      --  Message queues
      actuator-queue      Events-Ty (SIZE (0 .. actuator-queue-size)),
      controlsystem-queue Events-Ty (SIZE (0 .. controlsystem-queue-size)),
      host-queue          Events-Ty (SIZE (0 .. host-queue-size)),
      sensor-queue        Events-Ty (SIZE (0 .. sensor-queue-size)),

      actuator       Actuator-Context,
      controlsystem  Controlsystem-Context,
      host           Host-Context,
      sensor         Sensor-Context
   }

END

Simulation-Timers-DataView DEFINITIONS ::=
BEGIN

   TimerData ::= SEQUENCE {
      timer-enabled BOOLEAN,
      interval INTEGER (0 .. 50000)
   }

   AggregateTimerData ::= SEQUENCE {
      
      
      
      actuator SEQUENCE {
      },
      
      controlsystem SEQUENCE {
      },
      
      host SEQUENCE {
      },
      
      sensor SEQUENCE {
      },
      
      dummy-entry SEQUENCE {}
   }

END
