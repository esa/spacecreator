Modemanager-Datamodel DEFINITIONS ::=
BEGIN
--  This file was generated automatically by OpenGEODE
IMPORTS
   Dummy, DataItem, ActuatorIndex, ActuatorCommand, ActuatorStatus, ActuatorConfiguration, SystemCommand, SystemTelemetry FROM CDRDEMO-DATAVIEW
   T-Int32, T-UInt32, T-Int8, T-UInt8, T-Boolean, T-Null-Record FROM TASTE-BasicTypes
   PID-Range, PID FROM System-Dataview;

Modemanager-States ::= ENUMERATED {starting, operational, stopping, idle}

Modemanager-Context ::= SEQUENCE {
   state Modemanager-States,
   init-done BOOLEAN,
   sender PID,
   status1 ActuatorStatus,
   status2 ActuatorStatus,
   r DataItem,
   threshold1 DataItem,
   threshold2 DataItem,
   stc SystemCommand,
   stm SystemTelemetry
}

Modemanager-Systemcommand-Selection  ::= ENUMERATED {goToIdle-present(1), goToOperational-present(2), doReport-present(3)}
END
