Actuator-Datamodel DEFINITIONS ::=
BEGIN
--  This file was generated automatically by OpenGEODE
IMPORTS
   Dummy, DataItem, ActuatorIndex, ActuatorCommand, ActuatorStatus, ActuatorConfiguration, SystemCommand, SystemTelemetry FROM CDRDEMO-DATAVIEW
   T-Int32, T-UInt32, T-Int8, T-UInt8, T-Boolean, T-Null-Record FROM TASTE-BasicTypes
   PID-Range, PID FROM System-Dataview;

Actuator-States ::= ENUMERATED {armed, executing, standby}

Actuator-Context ::= SEQUENCE {
   state Actuator-States,
   init-done BOOLEAN,
   sender PID,
   cmd ActuatorCommand
}

Actuator-Systemcommand-Selection  ::= ENUMERATED {goToIdle-present(1), goToOperational-present(2)}
END
