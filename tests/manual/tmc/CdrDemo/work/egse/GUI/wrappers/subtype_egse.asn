EGSE-SUBTYPE DEFINITIONS ::=
BEGIN

IMPORTS SystemTelemetry FROM CDRDEMO-DATAVIEW


SystemCommand FROM CDRDEMO-DATAVIEW

 ;




Egse-systemtm-tm ::= SystemTelemetry




Egse-systemtc-tc ::= SystemCommand




END
