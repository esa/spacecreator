Actuator-Datamodel DEFINITIONS ::=
BEGIN
--  This file was generated automatically by OpenGEODE
IMPORTS
   Dummy, DataItem, ActuatorIndex, ActuatorCommand, ActuatorStatus, ActuatorConfiguration, SystemCommand, SystemTelemetry FROM CDRDEMO-DATAVIEW
   T-Int32, T-UInt32, T-Int8, T-UInt8, T-Boolean, T-Null-Record FROM TASTE-BasicTypes
   PID-Range, PID FROM System-Dataview;

Actuator-States ::= ENUMERATED {armed, executing, standby}

Actuator-Context ::= SEQUENCE {
   state Actuator-States,
   init-done BOOLEAN,
   sender PID,
   cmd ActuatorCommand
}

Actuator-Systemcommand-Selection  ::= ENUMERATED {goToIdle-present(1), goToOperational-present(2)}
END

Modemanager-Datamodel DEFINITIONS ::=
BEGIN
--  This file was generated automatically by OpenGEODE
IMPORTS
   Dummy, DataItem, ActuatorIndex, ActuatorCommand, ActuatorStatus, ActuatorConfiguration, SystemCommand, SystemTelemetry FROM CDRDEMO-DATAVIEW
   T-Int32, T-UInt32, T-Int8, T-UInt8, T-Boolean, T-Null-Record FROM TASTE-BasicTypes
   PID-Range, PID FROM System-Dataview;

Modemanager-States ::= ENUMERATED {idle, stopping, operational, starting}

Modemanager-Context ::= SEQUENCE {
   state Modemanager-States,
   init-done BOOLEAN,
   sender PID,
   status1 ActuatorStatus,
   status2 ActuatorStatus,
   r DataItem,
   threshold1 DataItem,
   threshold2 DataItem,
   stc SystemCommand,
   stm SystemTelemetry
}

Modemanager-Systemcommand-Selection  ::= ENUMERATED {goToIdle-present(1), goToOperational-present(2), doReport-present(3)}
END

CDRDEMO-DATAVIEW DEFINITIONS ::=
BEGIN

   Dummy ::= INTEGER(0..0)

   DataItem ::= INTEGER(0..255)

   ActuatorIndex ::= ENUMERATED {
       actuator1,
       actuator2
   }

   ActuatorCommand ::= ENUMERATED {
       actuatorArm,
       actuatorExecute,
       actuatorStandby
   }

    ActuatorStatus ::= ENUMERATED {
        actuatorArmed,
        actuatorExecuting,
        actuatorStandingBy
    }

    ActuatorConfiguration ::= SEQUENCE {
       threshold1 DataItem,
       threshold2 DataItem
    }

   SystemCommand ::= CHOICE
   {
       goToIdle Dummy,
       goToOperational ActuatorConfiguration,
       doReport Dummy
   }

    SystemTelemetry ::= SEQUENCE {
        reading DataItem,
        status1 ActuatorStatus,
        status2 ActuatorStatus
    }

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..6)

   -- List of functions (instances) present in the system
   PID ::= ENUMERATED {
       actuator,
       actuator1,
       actuator2,
       egse,
       modemanager,
       sensor,
       
       env
   }

END

EGSE-SUBTYPE DEFINITIONS ::=
BEGIN

IMPORTS SystemTelemetry FROM CDRDEMO-DATAVIEW


SystemCommand FROM CDRDEMO-DATAVIEW

 ;




Egse-systemtm-tm ::= SystemTelemetry




Egse-systemtc-tc ::= SystemCommand




END


Simulation-DataView DEFINITIONS ::=
BEGIN
   IMPORTS
      
      --  ASN.1 modules used by thread actuator1_actuatorTc
      ActuatorCommand FROM CDRDEMO-DATAVIEW
      
      --  ASN.1 modules used by thread actuator2_actuatorTc
      ActuatorCommand FROM CDRDEMO-DATAVIEW
      
      
      --  ASN.1 modules used by thread egse_systemTm
      SystemTelemetry FROM CDRDEMO-DATAVIEW
      
      --  ASN.1 modules used by thread modemanager_actuatorTm1
      ActuatorStatus FROM CDRDEMO-DATAVIEW
      
      --  ASN.1 modules used by thread modemanager_actuatorTm2
      ActuatorStatus FROM CDRDEMO-DATAVIEW
      
      --  ASN.1 modules used by thread modemanager_reading
      DataItem FROM CDRDEMO-DATAVIEW
      
      --  ASN.1 modules used by thread modemanager_systemTc
      SystemCommand FROM CDRDEMO-DATAVIEW
      
      
      -- Import generic integer type (used for timers)
      T-UInt32 FROM TASTE-BasicTypes
      PID      FROM System-Dataview
      -- Import timers
      AggregateTimerData FROM Simulation-Timers-DataView
      --  Import the SDL function states needed for the global system state
      Actuator-Context    FROM Actuator-Datamodel
      Actuator-Context    FROM Actuator-Datamodel
      Modemanager-Context FROM Modemanager-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Actuator1-Event ::= CHOICE {
      msg-in CHOICE {
         input-none SEQUENCE {},
         actuatortc SEQUENCE { tc ActuatorCommand}
      },
      msg-out CHOICE {
         actuatortm SEQUENCE { tm ActuatorStatus }
      }
   }
   
   Actuator2-Event ::= CHOICE {
      msg-in CHOICE {
         input-none SEQUENCE {},
         actuatortc SEQUENCE { tc ActuatorCommand}
      },
      msg-out CHOICE {
         actuatortm SEQUENCE { tm ActuatorStatus }
      }
   }
   
   Egse-Event ::= CHOICE {
      msg-in CHOICE {
         systemtm SEQUENCE { tm SystemTelemetry}
      },
      msg-out CHOICE {
         systemtc SEQUENCE { tc SystemCommand }
      }
   }
   
   Modemanager-Event ::= CHOICE {
      msg-in CHOICE {
         input-none SEQUENCE {},
         actuatortm1 SEQUENCE { tm ActuatorStatus},
         actuatortm2 SEQUENCE { tm ActuatorStatus},
         reading     SEQUENCE { x DataItem},
         systemtc    SEQUENCE { tc SystemCommand}
      },
      msg-out CHOICE {
         actuatortc1 SEQUENCE { tc ActuatorCommand },
         actuatortc2 SEQUENCE { tc ActuatorCommand },
         systemtm    SEQUENCE { tm SystemTelemetry }
      }
   }
   
   Sensor-Event ::= SEQUENCE {}  -- Synchronous function
   

   --  Current observer state flag (used by model checkers)
   Observer-State-Kind ::= ENUMERATED {
      regular-state,
      error-state,
      ignore-state,
      success-state
   }

   --  Event related to the execution of a PI or call of a RI in the functional code
   Function-Event ::= CHOICE {
      actuator1   Actuator1-Event,
      actuator2   Actuator2-Event,
      egse        Egse-Event,
      modemanager Modemanager-Event,
      sensor      Sensor-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   actuator1-queue-size INTEGER ::= 2
   actuator2-queue-size INTEGER ::= 2
   modemanager-queue-size INTEGER ::= 2

   System-State ::= SEQUENCE {
      --  Timers
      timers AggregateTimerData,
      --  Message queues
      actuator1-queue   Events-Ty (SIZE (0 .. actuator1-queue-size)),
      actuator2-queue   Events-Ty (SIZE (0 .. actuator2-queue-size)),
      modemanager-queue Events-Ty (SIZE (0 .. modemanager-queue-size)),

      actuator1    Actuator-Context,
      actuator2    Actuator-Context,
      modemanager  Modemanager-Context
   }

END

Simulation-Timers-DataView DEFINITIONS ::=
BEGIN

   TimerData ::= SEQUENCE {
      timer-enabled BOOLEAN,
      interval INTEGER (0 .. 50000)
   }

   AggregateTimerData ::= SEQUENCE {
      
      
      
      actuator1 SEQUENCE {
      },
      
      actuator2 SEQUENCE {
      },
      
      modemanager SEQUENCE {
      },
      
      dummy-entry SEQUENCE {}
   }

END
