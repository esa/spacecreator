Modemanager-Datamodel DEFINITIONS ::=
BEGIN
--  This file was generated automatically by OpenGEODE
IMPORTS
   TInteger, TConfig, TReport FROM BASICCDRDEMO-DATAVIEW
   T-Int32, T-UInt32, T-Int8, T-UInt8, T-Boolean, T-Null-Record FROM TASTE-BasicTypes
   PID-Range, PID FROM System-Dataview;

Modemanager-States ::= ENUMERATED {configured, uninitialized}

Modemanager-Context ::= SEQUENCE {
   state Modemanager-States,
   init-done BOOLEAN,
   sender PID,
   cfg TConfig,
   xin TInteger,
   xout TInteger,
   xfeedback TInteger,
   rprt TReport
}

END
