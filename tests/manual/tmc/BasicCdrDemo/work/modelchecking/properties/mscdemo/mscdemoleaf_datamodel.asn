Mscdemoleaf-Datamodel DEFINITIONS ::=
BEGIN
--  This file was generated automatically by OpenGEODE
IMPORTS
   Actuator-States, Actuator-Context FROM Actuator-Datamodel
   Modemanager-States, Modemanager-Context FROM Modemanager-Datamodel
   TInteger, TConfig, TReport FROM BASICCDRDEMO-DATAVIEW
   T-Int32, T-UInt32, T-Int8, T-UInt8, T-Boolean, T-Null-Record FROM TASTE-BasicTypes
   PID-Range, PID FROM System-Dataview
   Actuator-Event, Egse-Event, Modemanager-Event, Sensor-Event, Observer-State-Kind, Function-Event, Named-Function-Event, Interface-Event, Observable-Event, Events-Ty, System-State FROM Simulation-DataView
   TimerData, AggregateTimerData FROM Simulation-Timers-DataView;

Mscdemoleaf-States ::= ENUMERATED {s1, s2, s0}

Mscdemoleaf-Context ::= SEQUENCE {
   state Mscdemoleaf-States,
   init-done BOOLEAN,
   sender PID
}

Mscdemoleaf-Actuator-Event-Msg-In-Selection  ::= ENUMERATED {input-none-present(1), ctrl-present(2)}
Mscdemoleaf-Actuator-Event-Msg-Out-Selection  ::= ENUMERATED {feedback-present(1)}
Mscdemoleaf-Actuator-Event-Selection  ::= ENUMERATED {msg-in-present(1), msg-out-present(2)}
Mscdemoleaf-Sensor-Event-Msg-Out-Selection  ::= ENUMERATED {reading-present(1)}
Mscdemoleaf-Sensor-Event-Selection  ::= ENUMERATED {msg-out-present(1)}
Mscdemoleaf-Egse-Event-Msg-In-Selection  ::= ENUMERATED {tm-present(1)}
Mscdemoleaf-Egse-Event-Msg-Out-Selection  ::= ENUMERATED {tc-present(1)}
Mscdemoleaf-Egse-Event-Selection  ::= ENUMERATED {msg-in-present(1), msg-out-present(2)}
Mscdemoleaf-Modemanager-Event-Msg-In-Selection  ::= ENUMERATED {input-none-present(1), feedback-present(2), reading-present(3), tc-present(4)}
Mscdemoleaf-Modemanager-Event-Msg-Out-Selection  ::= ENUMERATED {ctrl-present(1), tm-present(2)}
Mscdemoleaf-Modemanager-Event-Selection  ::= ENUMERATED {msg-in-present(1), msg-out-present(2)}
Mscdemoleaf-Function-Event-Selection  ::= ENUMERATED {actuator-present(1), egse-present(2), modemanager-present(3), sensor-present(4)}
Mscdemoleaf-Observable-Event-Selection  ::= ENUMERATED {no-event-present(1), system-startup-present(2), input-event-present(3), output-event-present(4), unhandled-input-present(5)}
END
