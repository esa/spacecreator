EGSE-SUBTYPE DEFINITIONS ::=
BEGIN

IMPORTS TReport FROM BASICCDRDEMO-DATAVIEW


TConfig FROM BASICCDRDEMO-DATAVIEW

 ;




Egse-tm-reprt ::= TReport




Egse-tc-cfg ::= TConfig




END
SENSOR-SUBTYPE DEFINITIONS ::=
BEGIN

IMPORTS 

TInteger FROM BASICCDRDEMO-DATAVIEW

 ;







Sensor-reading-x ::= TInteger




END
