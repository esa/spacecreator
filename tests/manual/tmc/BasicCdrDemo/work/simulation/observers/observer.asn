Actuator-Datamodel DEFINITIONS ::=
BEGIN
--  This file was generated automatically by OpenGEODE
IMPORTS
   T-Integer, T-Config, T-Report FROM BASICCDRDEMO-DATAVIEW
   T-Int32, T-UInt32, T-Int8, T-UInt8, T-Boolean, T-Null-Record FROM TASTE-BasicTypes
   PID-Range, PID FROM System-Dataview;

Actuator-States ::= ENUMERATED {working, idle}

Actuator-Context ::= SEQUENCE {
   state Actuator-States,
   init-done BOOLEAN,
   sender PID,
   x T-Integer
}

END

Modemanager-Datamodel DEFINITIONS ::=
BEGIN
--  This file was generated automatically by OpenGEODE
IMPORTS
   T-Integer, T-Config, T-Report FROM BASICCDRDEMO-DATAVIEW
   T-Int32, T-UInt32, T-Int8, T-UInt8, T-Boolean, T-Null-Record FROM TASTE-BasicTypes
   PID-Range, PID FROM System-Dataview;

Modemanager-States ::= ENUMERATED {uninitialized, configured}

Modemanager-Context ::= SEQUENCE {
   state Modemanager-States,
   init-done BOOLEAN,
   sender PID,
   cfg T-Config,
   xin T-Integer,
   xout T-Integer,
   xfeedback T-Integer,
   rprt T-Report
}

END

BASICCDRDEMO-DATAVIEW DEFINITIONS ::=
BEGIN

   T-Integer ::= INTEGER (0 .. 1000000)

   T-Config ::= SEQUENCE {
       param-a T-Integer,
       param-b T-Integer
   }

   T-Report ::= SEQUENCE {
       reading T-Integer,
       ctrl T-Integer,
       feedback T-Integer
   }

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..4)

   -- List of functions (instances) present in the system
   PID ::= ENUMERATED {
       actuator,
       egse,
       modemanager,
       sensor,
       
       env
   }

END


Simulation-DataView DEFINITIONS ::=
BEGIN
   IMPORTS
      
      --  ASN.1 modules used by thread actuator_ctrl
      T-Integer FROM BASICCDRDEMO-DATAVIEW
      
      
      --  ASN.1 modules used by thread egse_tm
      T-Report FROM BASICCDRDEMO-DATAVIEW
      
      --  ASN.1 modules used by thread modemanager_feedback
      T-Integer FROM BASICCDRDEMO-DATAVIEW
      
      --  ASN.1 modules used by thread modemanager_reading
      T-Integer FROM BASICCDRDEMO-DATAVIEW
      
      --  ASN.1 modules used by thread modemanager_tc
      T-Config FROM BASICCDRDEMO-DATAVIEW
      
      
      -- Import generic integer type (used for timers)
      T-UInt32 FROM TASTE-BasicTypes
      PID      FROM System-Dataview
      -- Import timers
      AggregateTimerData FROM Simulation-Timers-DataView
      --  Import the SDL function states needed for the global system state
      Actuator-Context    FROM Actuator-Datamodel
      Modemanager-Context FROM Modemanager-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Actuator-Event ::= CHOICE {
      msg-in CHOICE {
         input-none SEQUENCE {},
         ctrl SEQUENCE { x T-Integer}
      },
      msg-out CHOICE {
         feedback SEQUENCE { x T-Integer }
      }
   }
   
   Egse-Event ::= CHOICE {
      msg-in CHOICE {
         tm SEQUENCE { reprt T-Report}
      },
      msg-out CHOICE {
         tc SEQUENCE { cfg T-Config }
      }
   }
   
   Modemanager-Event ::= CHOICE {
      msg-in CHOICE {
         input-none SEQUENCE {},
         feedback SEQUENCE { x T-Integer},
         reading  SEQUENCE { x T-Integer},
         tc       SEQUENCE { cfg T-Config}
      },
      msg-out CHOICE {
         ctrl SEQUENCE { x T-Integer },
         tm   SEQUENCE { reprt T-Report }
      }
   }
   
   Sensor-Event ::= CHOICE {
      msg-out CHOICE {
         reading SEQUENCE { x T-Integer }
      }
   }
   

   --  Current observer state flag (used by model checkers)
   Observer-State-Kind ::= ENUMERATED {
      regular-state,
      error-state,
      ignore-state,
      success-state
   }

   --  Event related to the execution of a PI or call of a RI in the functional code
   Function-Event ::= CHOICE {
      actuator    Actuator-Event,
      egse        Egse-Event,
      modemanager Modemanager-Event,
      sensor      Sensor-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   actuator-queue-size INTEGER ::= 2
   modemanager-queue-size INTEGER ::= 2

   System-State ::= SEQUENCE {
      --  Timers
      timers AggregateTimerData,
      --  Message queues
      actuator-queue    Events-Ty (SIZE (0 .. actuator-queue-size)),
      modemanager-queue Events-Ty (SIZE (0 .. modemanager-queue-size)),

      actuator     Actuator-Context,
      modemanager  Modemanager-Context
   }

END

Simulation-Timers-DataView DEFINITIONS ::=
BEGIN

   TimerData ::= SEQUENCE {
      timer-enabled BOOLEAN,
      interval INTEGER (0 .. 50000)
   }

   AggregateTimerData ::= SEQUENCE {
      
      
      
      actuator SEQUENCE {
      },
      
      modemanager SEQUENCE {
      },
      
      dummy-entry SEQUENCE {}
   }

END
