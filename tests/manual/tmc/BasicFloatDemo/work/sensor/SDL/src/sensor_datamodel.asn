Sensor-Datamodel DEFINITIONS ::=
BEGIN
--  This file was generated automatically by OpenGEODE
IMPORTS
   T-Int, T-Float FROM BASICFLOATDEMO-DATAVIEW
   T-Int32, T-UInt32, T-Int8, T-UInt8, T-Boolean, T-Null-Record FROM TASTE-BasicTypes
   PID-Range, PID FROM System-Dataview;

Sensor-States ::= ENUMERATED {wait}

Sensor-Context ::= SEQUENCE {
   state Sensor-States,
   init-done BOOLEAN,
   sender PID,
   x T-Float
}

END
