Actuator-Datamodel DEFINITIONS ::=
BEGIN
--  This file was generated automatically by OpenGEODE
IMPORTS
   T-Int, T-Float FROM BASICFLOATDEMO-DATAVIEW
   T-Int32, T-UInt32, T-Int8, T-UInt8, T-Boolean, T-Null-Record FROM TASTE-BasicTypes
   PID-Range, PID FROM System-Dataview;

Actuator-States ::= ENUMERATED {wait}

Actuator-Context ::= SEQUENCE {
   state Actuator-States,
   init-done BOOLEAN,
   sender PID,
   x T-Float
}

END

Sensor-Datamodel DEFINITIONS ::=
BEGIN
--  This file was generated automatically by OpenGEODE
IMPORTS
   T-Int, T-Float FROM BASICFLOATDEMO-DATAVIEW
   T-Int32, T-UInt32, T-Int8, T-UInt8, T-Boolean, T-Null-Record FROM TASTE-BasicTypes
   PID-Range, PID FROM System-Dataview;

Sensor-States ::= ENUMERATED {wait}

Sensor-Context ::= SEQUENCE {
   state Sensor-States,
   init-done BOOLEAN,
   sender PID,
   x T-Float
}

END

Systemcontrol-Datamodel DEFINITIONS ::=
BEGIN
--  This file was generated automatically by OpenGEODE
IMPORTS
   T-Int, T-Float FROM BASICFLOATDEMO-DATAVIEW
   T-Int32, T-UInt32, T-Int8, T-UInt8, T-Boolean, T-Null-Record FROM TASTE-BasicTypes
   PID-Range, PID FROM System-Dataview;

Systemcontrol-States ::= ENUMERATED {wait}

Systemcontrol-Context ::= SEQUENCE {
   state Systemcontrol-States,
   init-done BOOLEAN,
   sender PID,
   xin T-Float,
   lastx T-Float,
   xout T-Float
}

END

BASICFLOATDEMO-DATAVIEW DEFINITIONS ::=
BEGIN

   T-Int ::= INTEGER (-10000 .. 10000)
   T-Float ::= REAL(-10000 .. 10000)

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..4)

   -- List of functions (instances) present in the system
   PID ::= ENUMERATED {
       actuator,
       egse,
       sensor,
       systemcontrol,
       
       env
   }

END


Simulation-DataView DEFINITIONS ::=
BEGIN
   IMPORTS
      
      --  ASN.1 modules used by thread actuator_controlsignal
      T-Float FROM BASICFLOATDEMO-DATAVIEW
      
      
      --  ASN.1 modules used by thread egse_tm
      T-Int FROM BASICFLOATDEMO-DATAVIEW
      
      
      --  ASN.1 modules used by thread systemcontrol_reading
      T-Float FROM BASICFLOATDEMO-DATAVIEW
      
      
      --  ASN.1 modules used by thread systemcontrol_tc
      T-Int FROM BASICFLOATDEMO-DATAVIEW
      
      -- Import generic integer type (used for timers)
      T-UInt32 FROM TASTE-BasicTypes
      PID      FROM System-Dataview
      -- Import timers
      AggregateTimerData FROM Simulation-Timers-DataView
      --  Import the SDL function states needed for the global system state
      Actuator-Context      FROM Actuator-Datamodel
      Sensor-Context        FROM Sensor-Datamodel
      Systemcontrol-Context FROM Systemcontrol-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Actuator-Event ::= CHOICE {
      msg-in CHOICE {
         input-none SEQUENCE {},
         controlsignal SEQUENCE { x T-Float}
      },
      msg-out CHOICE {
         reporting SEQUENCE {   }
      }
   }
   
   Egse-Event ::= CHOICE {
      msg-in CHOICE {
         tm SEQUENCE { y T-Int}
      },
      msg-out CHOICE {
         tc SEQUENCE { x T-Int }
      }
   }
   
   Sensor-Event ::= CHOICE {
      msg-in CHOICE {
         input-none SEQUENCE {},
         trigger SEQUENCE {  }
      },
      msg-out CHOICE {
         reading SEQUENCE { x T-Float }
      }
   }
   Sensor-Periodic-Events ::=
      Periodic-Events {Sensor-Event, 1}
   
   sensor-periodic-events Sensor-Periodic-Events ::= {
      { period 1000, event msg-in: trigger : {} }
   }
   
   Systemcontrol-Event ::= CHOICE {
      msg-in CHOICE {
         input-none SEQUENCE {},
         reading   SEQUENCE { x T-Float},
         reporting SEQUENCE {  },
         tc        SEQUENCE { x T-Int}
      },
      msg-out CHOICE {
         controlsignal SEQUENCE { x T-Float },
         tm            SEQUENCE { y T-Int }
      }
   }
   

   --  Current observer state flag (used by model checkers)
   Observer-State-Kind ::= ENUMERATED {
      regular-state,
      error-state,
      ignore-state,
      success-state
   }

   --  Event related to the execution of a PI or call of a RI in the functional code
   Function-Event ::= CHOICE {
      actuator      Actuator-Event,
      egse          Egse-Event,
      sensor        Sensor-Event,
      systemcontrol Systemcontrol-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   actuator-queue-size INTEGER ::= 2
   sensor-queue-size INTEGER ::= 2
   systemcontrol-queue-size INTEGER ::= 2

   System-State ::= SEQUENCE {
      --  Timers
      timers AggregateTimerData,
      --  Message queues
      actuator-queue      Events-Ty (SIZE (0 .. actuator-queue-size)),
      sensor-queue        Events-Ty (SIZE (0 .. sensor-queue-size)),
      systemcontrol-queue Events-Ty (SIZE (0 .. systemcontrol-queue-size)),

      actuator       Actuator-Context,
      sensor         Sensor-Context,
      systemcontrol  Systemcontrol-Context
   }

END

Simulation-Timers-DataView DEFINITIONS ::=
BEGIN

   TimerData ::= SEQUENCE {
      timer-enabled BOOLEAN,
      interval INTEGER (0 .. 50000)
   }

   AggregateTimerData ::= SEQUENCE {
      
      
      
      actuator SEQUENCE {
      },
      
      sensor SEQUENCE {
      },
      
      systemcontrol SEQUENCE {
      },
      
      dummy-entry SEQUENCE {}
   }

END
