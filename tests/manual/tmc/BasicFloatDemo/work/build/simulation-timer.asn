Simulation-Timers-DataView DEFINITIONS ::=
BEGIN

   TimerData ::= SEQUENCE {
      timer-enabled BOOLEAN,
      interval INTEGER (0 .. 50000)
   }

   AggregateTimerData ::= SEQUENCE {
      
      
      
      actuator SEQUENCE {
      },
      
      sensor SEQUENCE {
      },
      
      systemcontrol SEQUENCE {
      },
      
      dummy-entry SEQUENCE {}
   }

END
