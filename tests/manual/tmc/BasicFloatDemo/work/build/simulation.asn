Simulation-DataView DEFINITIONS ::=
BEGIN
   IMPORTS
      
      --  ASN.1 modules used by thread actuator_controlsignal
      T-Float FROM BASICFLOATDEMO-DATAVIEW
      
      
      --  ASN.1 modules used by thread egse_tm
      T-Int FROM BASICFLOATDEMO-DATAVIEW
      
      
      --  ASN.1 modules used by thread systemcontrol_reading
      T-Float FROM BASICFLOATDEMO-DATAVIEW
      
      
      --  ASN.1 modules used by thread systemcontrol_tc
      T-Int FROM BASICFLOATDEMO-DATAVIEW
      
      -- Import generic integer type (used for timers)
      T-UInt32 FROM TASTE-BasicTypes
      PID      FROM System-Dataview
      -- Import timers
      AggregateTimerData FROM Simulation-Timers-DataView
      --  Import the SDL function states needed for the global system state
      Actuator-Context      FROM Actuator-Datamodel
      Sensor-Context        FROM Sensor-Datamodel
      Systemcontrol-Context FROM Systemcontrol-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Actuator-Event ::= CHOICE {
      msg-in CHOICE {
         input-none SEQUENCE {},
         controlsignal SEQUENCE { x T-Float}
      },
      msg-out CHOICE {
         reporting SEQUENCE {   }
      }
   }
   
   Egse-Event ::= CHOICE {
      msg-in CHOICE {
         tm SEQUENCE { y T-Int}
      },
      msg-out CHOICE {
         tc SEQUENCE { x T-Int }
      }
   }
   
   Sensor-Event ::= CHOICE {
      msg-in CHOICE {
         input-none SEQUENCE {},
         trigger SEQUENCE {  }
      },
      msg-out CHOICE {
         reading SEQUENCE { x T-Float }
      }
   }
   Sensor-Periodic-Events ::=
      Periodic-Events {Sensor-Event, 1}
   
   sensor-periodic-events Sensor-Periodic-Events ::= {
      { period 1000, event msg-in: trigger : {} }
   }
   
   Systemcontrol-Event ::= CHOICE {
      msg-in CHOICE {
         input-none SEQUENCE {},
         reading   SEQUENCE { x T-Float},
         reporting SEQUENCE {  },
         tc        SEQUENCE { x T-Int}
      },
      msg-out CHOICE {
         controlsignal SEQUENCE { x T-Float },
         tm            SEQUENCE { y T-Int }
      }
   }
   

   --  Current observer state flag (used by model checkers)
   Observer-State-Kind ::= ENUMERATED {
      regular-state,
      error-state,
      ignore-state,
      success-state
   }

   --  Event related to the execution of a PI or call of a RI in the functional code
   Function-Event ::= CHOICE {
      actuator      Actuator-Event,
      egse          Egse-Event,
      sensor        Sensor-Event,
      systemcontrol Systemcontrol-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   actuator-queue-size INTEGER ::= 2
   sensor-queue-size INTEGER ::= 2
   systemcontrol-queue-size INTEGER ::= 2

   System-State ::= SEQUENCE {
      --  Timers
      timers AggregateTimerData,
      --  Message queues
      actuator-queue      Events-Ty (SIZE (0 .. actuator-queue-size)),
      sensor-queue        Events-Ty (SIZE (0 .. sensor-queue-size)),
      systemcontrol-queue Events-Ty (SIZE (0 .. systemcontrol-queue-size)),

      actuator       Actuator-Context,
      sensor         Sensor-Context,
      systemcontrol  Systemcontrol-Context
   }

END
