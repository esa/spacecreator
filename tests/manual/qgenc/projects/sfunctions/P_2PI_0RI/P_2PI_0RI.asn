P-2PI-0RI-DATAVIEW DEFINITIONS ::=
BEGIN

    MyInteger   ::= INTEGER (0..255)
    MyReal      ::= REAL (0.0 .. 1000.0)
    MyBool      ::= BOOLEAN
    MySeqOf     ::= SEQUENCE (SIZE (2)) OF MyInteger

    MySeq ::= SEQUENCE
    {
        myInteger MyInteger,
        myReal    MyReal,
        myBool    MyBool,
        mySeqOfVar MySeqOf
    }

    MyInteger2   ::= INTEGER (0..255)
    MyReal2      ::= REAL (0.0 .. 1000.0)
    MyBool2      ::= BOOLEAN
    MySeqOf2     ::= SEQUENCE (SIZE (2)) OF MyInteger2

    MySeq2 ::= SEQUENCE
    {
        myInteger MyInteger2,
        myReal    MyReal2,
        myBool    MyBool2,
        mySeqOfVar MySeqOf2
    }

END
