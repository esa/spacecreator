Com-n7space-SimpleDataTypes DEFINITIONS ::= BEGIN
UnsignedInteger8 ::= INTEGER(0 .. 255)
SignedInteger16 ::= INTEGER(-32768 .. 32767)
BasicBoolean ::= BOOLEAN
InvertedBoolean ::= BOOLEAN
Float32 ::= REAL(1.17549e-38 .. 3.40282e+38)
UnsignedFloat80 ::= REAL(0 .. 1.79769e+308)
VariableSizeBLOB ::= BIT STRING(SIZE(0 .. 128))
FixedSizeBLOB ::= BIT STRING(SIZE(64))
FixedSizeAsciiString ::= IA5String(SIZE(32))
CString ::= IA5String(SIZE(0 .. 64))
ASCIIString ::= IA5String(SIZE(0 .. 32))
SimpleEnumeration ::= ENUMERATED
{
    value1(12),
    value2(15),
    negativeValue(-12)
}
END
