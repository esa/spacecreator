COM-N7SPACE-COMMANDARGUMENTS-COMPONENT DEFINITIONS ::= BEGIN
IMPORTS
MyFloat FROM COM-N7SPACE-COMMANDARGUMENTS
MyInteger FROM COM-N7SPACE-COMMANDARGUMENTS
;
Component-GenericInterfaceIntegerPI-GenericType ::= MyInteger
Component-GenericInterfaceIntegerPI-GenericCommand-Type ::= SEQUENCE
{
    genericArgument1 Component-GenericInterfaceIntegerPI-GenericType,
    genericArgument2 Component-GenericInterfaceIntegerPI-GenericType
}
Component-GenericInterfaceIntegerReusePI-GenericType ::= MyInteger
Component-GenericInterfaceIntegerReusePI-GenericCommand-Type ::= SEQUENCE
{
    genericArgument1 Component-GenericInterfaceIntegerReusePI-GenericType,
    genericArgument2 Component-GenericInterfaceIntegerReusePI-GenericType
}
Component-GenericInterfaceFloatPI-GenericType ::= MyFloat
Component-GenericInterfaceFloatPI-GenericCommand-Type ::= SEQUENCE
{
    genericArgument1 Component-GenericInterfaceFloatPI-GenericType,
    genericArgument2 Component-GenericInterfaceFloatPI-GenericType
}
END
