COM-N7SPACE-COMMANDARGUMENTS DEFINITIONS ::= BEGIN
MyInteger ::= INTEGER(0 .. 255)
MyFloat ::= REAL(-3.40282e+38 .. 3.40282e+38)
AsyncInterface-AsyncInCommand-Type ::= SEQUENCE
{
    asyncInArgument1 MyInteger,
    asyncInArgument2 MyInteger
}
AsyncInterface-AsyncOutCommand-Type ::= SEQUENCE
{
    asyncOutArgument1 MyInteger,
    asyncOutArgument2 MyInteger
}
MyIntegerArray-10 ::= SEQUENCE (SIZE(10)) OF MyInteger
ArrayInterface-ArrayCommand1-Type ::= SEQUENCE
{
    arrayArgument1 MyIntegerArray-10
}
MyIntegerArray-20 ::= SEQUENCE (SIZE(20)) OF MyInteger
ArrayInterface-ArrayCommand2-Type ::= SEQUENCE
{
    arrayArgument1 MyIntegerArray-20
}
ArrayInterface-ArrayCommand3-Type ::= SEQUENCE
{
    arrayArgument1 MyIntegerArray-10
}
END
