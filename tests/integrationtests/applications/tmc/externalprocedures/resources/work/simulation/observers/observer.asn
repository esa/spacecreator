Ponger-Datamodel DEFINITIONS ::=
BEGIN
--  This file was generated automatically by OpenGEODE
IMPORTS
   MyInteger FROM EXTERNAL-PROCEDURES-DATAVIEW
   T-Int32, T-UInt32, T-Int8, T-UInt8, T-Boolean, T-Null-Record FROM TASTE-BasicTypes
   PID-Range, PID FROM System-Dataview;

Ponger-States ::= ENUMERATED {wait}

Ponger-Context ::= SEQUENCE {
   state Ponger-States,
   init-done BOOLEAN,
   sender PID,
   offspring PID,
   pingarg MyInteger,
   pongarg MyInteger,
   argoutval MyInteger
}

END

EXTERNAL-PROCEDURES-DATAVIEW DEFINITIONS ::=
BEGIN
   MyInteger ::= INTEGER (0 .. 5)
END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..3)

   -- List of functions (instances) present in the system
   PID ::= ENUMERATED {
       pinger,
       
       ponger,
       
       utils,
       
       
       env
   }

END

PINGER-SUBTYPE DEFINITIONS ::=
BEGIN

IMPORTS 

MyInteger FROM EXTERNAL-PROCEDURES-DATAVIEW

 ;







Pinger-ping-pingArg ::= MyInteger




END


Simulation-DataView DEFINITIONS ::=
BEGIN
   IMPORTS
      
      
      --  ASN.1 modules used by thread ponger_Ping
      MyInteger FROM EXTERNAL-PROCEDURES-DATAVIEW
      
      -- Import generic integer type (used for timers)
      T-UInt32 FROM TASTE-BasicTypes
      PID      FROM System-Dataview
      -- Import timers
      AggregateTimerData FROM Simulation-Timers-DataView
      --  Import the SDL function states needed for the global system state
      Ponger-Context FROM Ponger-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Pinger-Event ::= CHOICE {
      msg-out CHOICE {
         ping SEQUENCE { pingarg MyInteger }
      }
   }
   
   Ponger-Event ::= CHOICE {
      -- Lang: SDL TRUE FALSE
      msg-in CHOICE {
         input-none SEQUENCE {},
         ping SEQUENCE { pingarg MyInteger}
      }
   }
   
   Utils-Event ::= SEQUENCE {}  -- Synchronous function
   

   --  Current observer state flag (used by model checkers)
   Observer-State-Kind ::= ENUMERATED {
      regular-state,
      error-state,
      ignore-state,
      success-state
   }

   --  Event related to the execution of a PI or call of a RI in the functional code
   Function-Event ::= CHOICE {
      pinger Pinger-Event,
      ponger Ponger-Event,
      utils  Utils-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   ponger-queue-size INTEGER ::= 2

   System-State ::= SEQUENCE {
      --  Timers
      timers AggregateTimerData,
      --  Message queues
      ponger-queue Events-Ty (SIZE (0 .. ponger-queue-size)),

      ponger  Ponger-Context
   }

   --  List the GUI functions (environment of the system being simulated)
   System-GUIs ::= ENUMERATED {
      pinger
   }

END

Simulation-Timers-DataView DEFINITIONS ::=
BEGIN

   TimerData ::= SEQUENCE {
      timer-enabled BOOLEAN,
      interval INTEGER (0 .. 50000)
   }

   AggregateTimerData ::= SEQUENCE {
      
      
      
      ponger SEQUENCE {
      },
      
      dummy-entry SEQUENCE {}
   }

END
