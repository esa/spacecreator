BCAPP-SUBTYPE DEFINITIONS ::=
BEGIN

IMPORTS 

T-UART-DLC-SDU FROM UART-DLC

 ;







Bcapp-dlctxsdu-p1 ::= T-UART-DLC-SDU




END
RTAPP-SUBTYPE DEFINITIONS ::=
BEGIN

IMPORTS T-UART-DLC-RxErrorCode FROM UART-DLC




T-UART-DLC-SDU FROM UART-DLC


 ;




Rtapp-dlcrxerror-p1 ::= T-UART-DLC-RxErrorCode




Rtapp-dlcrxsdu-p1 ::= T-UART-DLC-SDU







END
CHANNELEFFECTS-SUBTYPE DEFINITIONS ::=
BEGIN

IMPORTS 

UINT8 FROM Basic-Types

 ;







Channeleffects-corruptchar-p1 ::= UINT8




END
