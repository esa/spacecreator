Basic-Types DEFINITIONS ::=
BEGIN

-- Basic types -- ToDo factor out
UINT40 ::= INTEGER (0 .. 1099511627775)
UINT32 ::= INTEGER (0 .. 4294967295)
UINT24 ::= INTEGER (0 .. 16777215)
UINT16 ::= INTEGER (0 .. 65535)
UINT14 ::= INTEGER (0 .. 16383)
UINT12 ::= INTEGER (0 .. 4095)
UINT11 ::= INTEGER (0 .. 2047)
UINT10 ::= INTEGER (0 .. 1023)
UINT8  ::= INTEGER (0 .. 255)
UINT7  ::= INTEGER (0 .. 127)
UINT6  ::= INTEGER (0 .. 63)
UINT5  ::= INTEGER (0 .. 31)
UINT4  ::= INTEGER (0 .. 15)
UINT3  ::= INTEGER (0 .. 7)
UINT2  ::= INTEGER (0 .. 3)
UINT1  ::= INTEGER (0 .. 1)
T-Bit  ::= UINT1

INT16 ::= INTEGER (-32768 .. 32767)
INT32 ::= INTEGER (-2147483648 .. 2147483647)
INT24 ::= INTEGER (-8388608 .. 8388607)

T-OCTET ::= OCTET STRING (SIZE(1))

END
