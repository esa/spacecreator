Sharedmemory-Datamodel DEFINITIONS ::=
BEGIN
--  This file was generated automatically by OpenGEODE
IMPORTS
   T-UInt16, T-WriteAccess, T-ByteArray, T-MemBuffer, T-WriteRequest, T-ProcID FROM DEKKER1-DATAVIEW
   T-Int32, T-UInt32, T-Int8, T-UInt8, T-Boolean, T-Null-Record FROM TASTE-BasicTypes
   PID-Range, PID FROM System-Dataview;

Sharedmemory-States ::= ENUMERATED {idle}

Sharedmemory-Context ::= SEQUENCE {
   state Sharedmemory-States,
   init-done BOOLEAN,
   sender PID,
   offspring PID,
   membuffer T-MemBuffer,
   writeaccess T-WriteAccess
}

END
