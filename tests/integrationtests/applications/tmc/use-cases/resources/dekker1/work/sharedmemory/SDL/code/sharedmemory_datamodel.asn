Sharedmemory-Datamodel DEFINITIONS ::=
BEGIN
IMPORTS
   T-UInt8, T-UInt16, T-Boolean, T-WriteAccess, T-ByteArray, T-MemBuffer, T-WriteRequest, T-ProcID FROM DEKKER1-DATAVIEW
   T-Int32, T-UInt32, T-Int8, TASTE-BasicTypes-T-UInt8, TASTE-BasicTypes-T-Boolean, T-Null-Record FROM TASTE-BasicTypes;

Sharedmemory-States ::= ENUMERATED {idle}

Sharedmemory-Context ::= SEQUENCE {
   state Sharedmemory-States,
   init-done BOOLEAN,
   membuffer T-MemBuffer,
   writeaccess T-WriteAccess
}

END
