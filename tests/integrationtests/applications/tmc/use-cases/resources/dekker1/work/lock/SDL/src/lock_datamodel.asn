Lock-Datamodel DEFINITIONS ::=
BEGIN
--  This file was generated automatically by OpenGEODE
IMPORTS
   T-UInt16, T-WriteAccess, T-ByteArray, T-MemBuffer, T-WriteRequest, T-ProcID FROM DEKKER1-DATAVIEW
   T-Int32, T-UInt32, T-Int8, T-UInt8, T-Boolean, T-Null-Record FROM TASTE-BasicTypes
   PID-Range, PID FROM System-Dataview;

Lock-States ::= ENUMERATED {writing, wait-turn, wait-nocontention, idle}

Lock-Context ::= SEQUENCE {
   state Lock-States,
   init-done BOOLEAN,
   sender PID,
   offspring PID,
   remotewantstoenter T-Boolean,
   writesize T-UInt8,
   myprocid T-ProcID,
   remoteprocid T-ProcID,
   turn T-ProcID,
   mywritevalue T-WriteAccess,
   writecount T-UInt8,
   turnerror T-Boolean,
   contentionerror T-Boolean,
   writerequest T-WriteRequest,
   startaddress T-UInt16
}

END
