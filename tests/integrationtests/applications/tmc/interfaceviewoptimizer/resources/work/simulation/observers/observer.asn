-- Dummy data model for the timer manager (needed to populate observer.asn)
Demo-timer-manager-Datamodel DEFINITIONS ::=
BEGIN
Demo-timer-manager-States ::= ENUMERATED {wait}

Demo-timer-manager-Context ::= SEQUENCE {
   state Demo-timer-manager-States
}

END

Pinger-Datamodel DEFINITIONS ::=
BEGIN
--  This file was generated automatically by OpenGEODE
IMPORTS
   MyInteger FROM ENVIRONMENT-SELECTOR-DATAVIEW
   T-Int32, T-UInt32, T-Int8, T-UInt8, T-Boolean, T-Null-Record FROM TASTE-BasicTypes
   PID-Range, PID FROM System-Dataview
   Context-pinger FROM Context-pinger;

Pinger-States ::= ENUMERATED {wait}

Pinger-Context ::= SEQUENCE {
   state Pinger-States,
   init-done BOOLEAN,
   sender PID,
   offspring PID,
   value MyInteger,
   result MyInteger
}

END

Context-pinger DEFINITIONS ::=
BEGIN
   IMPORTS
      T-Int8 FROM TASTE-BasicTypes;

--  Group all context parameters of this function in a record
Context-pinger ::= SEQUENCE {
   pingerparam T-Int8

}

--  Declare a constant with the values set by the user in the interface view
pinger-ctxt Context-pinger ::= {
   pingerparam 2

}
END

Ponger-Datamodel DEFINITIONS ::=
BEGIN
--  This file was generated automatically by OpenGEODE
IMPORTS
   MyInteger FROM ENVIRONMENT-SELECTOR-DATAVIEW
   T-Int32, T-UInt32, T-Int8, T-UInt8, T-Boolean, T-Null-Record FROM TASTE-BasicTypes
   PID-Range, PID FROM System-Dataview
   Context-ponger FROM Context-ponger;

Ponger-States ::= ENUMERATED {wait}

Ponger-Context ::= SEQUENCE {
   state Ponger-States,
   init-done BOOLEAN,
   sender PID,
   offspring PID,
   pingarg MyInteger
}

END

Context-ponger DEFINITIONS ::=
BEGIN
   IMPORTS
      T-Int8 FROM TASTE-BasicTypes;

--  Group all context parameters of this function in a record
Context-ponger ::= SEQUENCE {
   pongerparam T-Int8

}

--  Declare a constant with the values set by the user in the interface view
ponger-ctxt Context-ponger ::= {
   pongerparam 12

}
END

ENVIRONMENT-SELECTOR-DATAVIEW DEFINITIONS ::=
BEGIN

   MyInteger ::= INTEGER (0 .. 10)

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..4)

   -- List of functions (instances) present in the system
   PID ::= ENUMERATED {
       clock,
       
       pinger,
       
       ponger,
       
       demo-timer-manager,
       
       
       env
   }

END

CLOCK-SUBTYPE DEFINITIONS ::=
BEGIN

IMPORTS 

 ;










END


Simulation-DataView DEFINITIONS ::=
BEGIN
   IMPORTS
      
      
      
      
      
      
      --  ASN.1 modules used by thread ponger_PingInterface
      MyInteger FROM ENVIRONMENT-SELECTOR-DATAVIEW
      
      
      -- Import generic integer type (used for timers)
      T-UInt32 FROM TASTE-BasicTypes
      PID      FROM System-Dataview
      -- Import timers
      AggregateTimerData FROM Simulation-Timers-DataView
      --  Import the SDL function states needed for the global system state
      Demo-timer-manager-Context FROM Demo-timer-manager-Datamodel
      Pinger-Context             FROM Pinger-Datamodel
      Ponger-Context             FROM Ponger-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Clock-Event ::= CHOICE {
      msg-out CHOICE {
         clockinterface SEQUENCE {   }
      }
   }
   
   Demo-Timer-Manager-Event ::= CHOICE {
      msg-out CHOICE {
         pinger-pingertimer       SEQUENCE {   },
         pinger-pingertimer-reset SEQUENCE {   },
         pinger-pingertimer-set   SEQUENCE { val T-UInt32 },
         ponger-pongertimer       SEQUENCE {   },
         ponger-pongertimer-reset SEQUENCE {   },
         ponger-pongertimer-set   SEQUENCE { val T-UInt32 }
      }
   }
   
   Pinger-Event ::= CHOICE {
      -- Lang: SDL TRUE TRUE
      msg-in CHOICE {
         input-none SEQUENCE {},
         clockinterface        SEQUENCE {  },
         pingercyclicinterface SEQUENCE {  },
         pingertimer SEQUENCE {}
      },
      msg-out CHOICE {
         pinginterface SEQUENCE { arg MyInteger }
      }
   }
   Pinger-Periodic-Events ::=
      Periodic-Events {Pinger-Event, 1}
   
   pinger-periodic-events Pinger-Periodic-Events ::= {
      { period 1000, event msg-in: pingercyclicinterface : {} }
   }
   
   Ponger-Event ::= CHOICE {
      -- Lang: SDL TRUE TRUE
      msg-in CHOICE {
         input-none SEQUENCE {},
         pinginterface SEQUENCE { arg MyInteger},
         pongertimer SEQUENCE {}
      }
   }
   

   --  Current observer state flag (used by model checkers)
   Observer-State-Kind ::= ENUMERATED {
      regular-state,
      error-state,
      ignore-state,
      success-state
   }

   --  Event related to the execution of a PI or call of a RI in the functional code
   Function-Event ::= CHOICE {
      clock              Clock-Event,
      demo-timer-manager Demo-Timer-Manager-Event,
      pinger             Pinger-Event,
      ponger             Ponger-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   pinger-queue-size INTEGER ::= 2
   ponger-queue-size INTEGER ::= 2

   System-State ::= SEQUENCE {
      --  Timers
      timers AggregateTimerData,
      --  Message queues
      pinger-queue Events-Ty (SIZE (0 .. pinger-queue-size)),
      ponger-queue Events-Ty (SIZE (0 .. ponger-queue-size)),

      demo-timer-manager  Demo-timer-manager-Context,
      pinger              Pinger-Context,
      ponger              Ponger-Context
   }

   --  List the GUI functions (environment of the system being simulated)
   System-GUIs ::= ENUMERATED {
      clock
   }

END

Simulation-Timers-DataView DEFINITIONS ::=
BEGIN

   TimerData ::= SEQUENCE {
      timer-enabled BOOLEAN,
      interval INTEGER (0 .. 50000)
   }

   AggregateTimerData ::= SEQUENCE {
      
      
      
      pinger SEQUENCE {
         pingertimer TimerData
      
      },
      
      ponger SEQUENCE {
         pongertimer TimerData
      
      },
      
      dummy-entry SEQUENCE {}
   }

END
