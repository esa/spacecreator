Ponger-Datamodel DEFINITIONS ::=
BEGIN
IMPORTS
   MyInteger FROM ENVIRONMENT-SELECTOR-DATAVIEW
   T-Int32, T-UInt32, T-Int8, T-UInt8, T-Boolean, T-Null-Record FROM TASTE-BasicTypes;

Ponger-States ::= ENUMERATED {wait}

Ponger-Context ::= SEQUENCE {
   state Ponger-States,
   init-done BOOLEAN,
   result MyInteger,
   arg MyInteger
}

END
