Sat-Datamodel DEFINITIONS ::=
BEGIN
--  This file was generated automatically by OpenGEODE
IMPORTS
   MyInteger FROM NAME-MATCHING-DATAVIEW
   T-Int32, T-UInt32, T-Int8, T-UInt8, T-Boolean, T-Null-Record, T-Runtime-Error FROM TASTE-BasicTypes
   PID-Range, PID FROM System-Dataview;

Sat-States ::= ENUMERATED {busy, idle}

Sat-Context ::= SEQUENCE {
   state Sat-States,
   init-done BOOLEAN,
   sender PID,
   offspring PID,
   param MyInteger
}

Sat-T-Runtime-Error-Selection ::= ENUMERATED {noerror-present(1), encodeerror-present(2), decodeerror-present(3)}
END
