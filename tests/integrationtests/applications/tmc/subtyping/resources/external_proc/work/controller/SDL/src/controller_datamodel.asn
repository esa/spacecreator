Controller-Datamodel DEFINITIONS ::=
BEGIN
--  This file was generated automatically by OpenGEODE
IMPORTS
   MyInteger FROM EXTERNALPROC-DATAVIEW
   T-Int32, T-UInt32, T-Int8, T-UInt8, T-Boolean, T-Null-Record FROM TASTE-BasicTypes
   PID FROM System-Dataview;

Controller-States ::= ENUMERATED {wait, testprotected, error, finished}

Controller-Context ::= SEQUENCE {
   state Controller-States,
   init-done BOOLEAN,
   param-protected-x MyInteger,
   param-protected-y MyInteger,
   param-unprotected-x MyInteger,
   param-unprotected-y MyInteger
}

END
