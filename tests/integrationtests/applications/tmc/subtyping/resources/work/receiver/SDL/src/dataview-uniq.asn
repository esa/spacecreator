TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


USERDEFINED-TYPES-DATAVIEW DEFINITIONS ::=
BEGIN
    MyInteger ::= INTEGER (0 .. 10)
    MyBetterInteger ::= MyInteger (2 .. 8)
    MyArray ::= SEQUENCE (SIZE(0..10)) OF MyBetterInteger
END
