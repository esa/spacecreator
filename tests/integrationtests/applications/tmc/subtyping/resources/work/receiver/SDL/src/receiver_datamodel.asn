Receiver-Datamodel DEFINITIONS ::=
BEGIN
--  This file was generated automatically by OpenGEODE
IMPORTS
   T-Int32, T-UInt32, T-Int8, T-UInt8, T-Boolean, T-Null-Record FROM TASTE-BasicTypes
   MyInteger, MyBetterInteger, MyArray FROM USERDEFINED-TYPES-DATAVIEW
   Pinger-pong-pongArg, Pinger-pongbutarray-pongArg, Pinger-ping-pingArg FROM PINGER-SUBTYPE;

Receiver-States ::= ENUMERATED {wait}

Receiver-Context ::= SEQUENCE {
   state Receiver-States,
   init-done BOOLEAN,
   pingarg MyBetterInteger,
   temp MyArray
}

END
