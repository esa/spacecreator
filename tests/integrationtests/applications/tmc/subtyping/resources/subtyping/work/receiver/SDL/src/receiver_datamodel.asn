Receiver-Datamodel DEFINITIONS ::=
BEGIN
--  This file was generated automatically by OpenGEODE
IMPORTS
   MyInteger, MyBetterInteger, MyArray FROM SUBTYPING-DATAVIEW
   T-Int32, T-UInt32, T-Int8, T-UInt8, T-Boolean, T-Null-Record FROM TASTE-BasicTypes
   PID-Range, PID FROM System-Dataview;

Receiver-States ::= ENUMERATED {wait, ok}

Receiver-Context ::= SEQUENCE {
   state Receiver-States,
   init-done BOOLEAN,
   sender PID,
   offspring PID,
   pingarg MyBetterInteger,
   pingtmp MyBetterInteger,
   pingbutarrayarg MyArray,
   pingbutarraytmp MyArray
}

END
