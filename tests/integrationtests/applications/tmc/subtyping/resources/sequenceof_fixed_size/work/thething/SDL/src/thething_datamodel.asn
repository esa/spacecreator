Thething-Datamodel DEFINITIONS ::=
BEGIN
--  This file was generated automatically by OpenGEODE
IMPORTS
   MyInteger, MyArray FROM SEQUENCEOF-SUBTYPES-DATAVIEW
   T-Int32, T-UInt32, T-Int8, T-UInt8, T-Boolean, T-Null-Record FROM TASTE-BasicTypes
   PID-Range, PID FROM System-Dataview;

Thething-States ::= ENUMERATED {wait}

Thething-Context ::= SEQUENCE {
   state Thething-States,
   init-done BOOLEAN,
   sender PID,
   offspring PID,
   arg MyArray,
   result MyArray
}

END
