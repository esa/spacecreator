Function-2-Datamodel DEFINITIONS ::=
BEGIN
--  This file was generated automatically by OpenGEODE
IMPORTS
   MyInteger FROM CLEANDATA-DATAVIEW
   T-Int32, T-UInt32, T-Int8, T-UInt8, T-Boolean, T-Null-Record FROM TASTE-BasicTypes
   PID-Range, PID FROM System-Dataview;

Function-2-States ::= ENUMERATED {wait}

Function-2-Context ::= SEQUENCE {
   state Function-2-States,
   init-done BOOLEAN,
   sender PID,
   offspring PID
}

END

CLEANDATA-DATAVIEW DEFINITIONS ::=
BEGIN

   MyInteger ::= INTEGER (0 .. 2)

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..2)

   -- List of functions (instances) present in the system
   PID ::= ENUMERATED {
       function-1,
       
       function-2,
       
       
       env
   }

END

FUNCTION-1-SUBTYPE DEFINITIONS ::=
BEGIN

IMPORTS MyInteger FROM CLEANDATA-DATAVIEW


MyInteger FROM CLEANDATA-DATAVIEW

 ;




Function-1-pi-2-p1 ::= MyInteger




Function-1-pi-1-p1 ::= MyInteger




END


Simulation-DataView DEFINITIONS ::=
BEGIN
   IMPORTS
      
      --  ASN.1 modules used by thread function_1_PI_2
      MyInteger FROM CLEANDATA-DATAVIEW
      
      
      --  ASN.1 modules used by thread function_2_PI_1
      MyInteger FROM CLEANDATA-DATAVIEW
      
      -- Import generic integer type (used for timers)
      T-UInt32 FROM TASTE-BasicTypes
      PID      FROM System-Dataview
      -- Import timers
      AggregateTimerData FROM Simulation-Timers-DataView
      --  Import the SDL function states needed for the global system state
      Function-2-Context FROM Function-2-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Function-1-Event ::= CHOICE {
      -- Lang: GUI TRUE FALSE
      msg-in CHOICE {
         pi-2 SEQUENCE { p1 MyInteger}
      },
      msg-out CHOICE {
         pi-1 SEQUENCE { p1 MyInteger }
      }
   }
   
   Function-2-Event ::= CHOICE {
      -- Lang: SDL TRUE FALSE
      msg-in CHOICE {
         input-none SEQUENCE {},
         pi-1 SEQUENCE { p1 MyInteger}
      },
      msg-out CHOICE {
         pi-2 SEQUENCE { p1 MyInteger }
      }
   }
   

   --  Current observer state flag (used by model checkers)
   Observer-State-Kind ::= ENUMERATED {
      regular-state,
      error-state,
      ignore-state,
      success-state
   }

   --  Event related to the execution of a PI or call of a RI in the functional code
   Function-Event ::= CHOICE {
      function-1 Function-1-Event,
      function-2 Function-2-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   function-2-queue-size INTEGER ::= 2

   System-State ::= SEQUENCE {
      --  Timers
      timers AggregateTimerData,
      --  Message queues
      function-2-queue Events-Ty (SIZE (0 .. function-2-queue-size)),

      function-2  Function-2-Context
   }

   --  List the GUI functions (environment of the system being simulated)
   System-GUIs ::= ENUMERATED {
      function-1
   }

END

Simulation-Timers-DataView DEFINITIONS ::=
BEGIN

   TimerData ::= SEQUENCE {
      timer-enabled BOOLEAN,
      interval INTEGER (0 .. 50000)
   }

   AggregateTimerData ::= SEQUENCE {
      
      
      
      function-2 SEQUENCE {
      },
      
      dummy-entry SEQUENCE {}
   }

END
