Pinger-Datamodel DEFINITIONS ::=
BEGIN
IMPORTS
   MyInteger FROM ENVIRONMENT-SELECTOR-DATAVIEW
   T-Int32, T-UInt32, T-Int8, T-UInt8, T-Boolean, T-Null-Record FROM TASTE-BasicTypes;

Pinger-States ::= ENUMERATED {wait}

Pinger-Context ::= SEQUENCE {
   state Pinger-States,
   init-done BOOLEAN,
   value MyInteger,
   result MyInteger
}

END
