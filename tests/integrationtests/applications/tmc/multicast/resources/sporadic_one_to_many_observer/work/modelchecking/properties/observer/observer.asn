Actuator1-Datamodel DEFINITIONS ::=
BEGIN
--  This file was generated automatically by OpenGEODE
IMPORTS
   MyInteger FROM SPORADIC-ONE-TO-MANY-OBSERVER-DATAVIEW
   T-Int32, T-UInt32, T-Int8, T-UInt8, T-Boolean, T-Null-Record FROM TASTE-BasicTypes
   PID-Range, PID FROM System-Dataview;

Actuator1-States ::= ENUMERATED {wait}

Actuator1-Context ::= SEQUENCE {
   state Actuator1-States,
   init-done BOOLEAN,
   sender PID,
   offspring PID,
   param MyInteger
}

END

Actuator2-Datamodel DEFINITIONS ::=
BEGIN
--  This file was generated automatically by OpenGEODE
IMPORTS
   MyInteger FROM SPORADIC-ONE-TO-MANY-OBSERVER-DATAVIEW
   T-Int32, T-UInt32, T-Int8, T-UInt8, T-Boolean, T-Null-Record FROM TASTE-BasicTypes
   PID-Range, PID FROM System-Dataview;

Actuator2-States ::= ENUMERATED {wait}

Actuator2-Context ::= SEQUENCE {
   state Actuator2-States,
   init-done BOOLEAN,
   sender PID,
   offspring PID,
   param MyInteger
}

END

Controller-Datamodel DEFINITIONS ::=
BEGIN
--  This file was generated automatically by OpenGEODE
IMPORTS
   MyInteger FROM SPORADIC-ONE-TO-MANY-OBSERVER-DATAVIEW
   T-Int32, T-UInt32, T-Int8, T-UInt8, T-Boolean, T-Null-Record FROM TASTE-BasicTypes
   PID-Range, PID FROM System-Dataview;

Controller-States ::= ENUMERATED {waitforboth, finished, waitfor1, waitfor2}

Controller-Context ::= SEQUENCE {
   state Controller-States,
   init-done BOOLEAN,
   sender PID,
   offspring PID,
   my-value MyInteger
}

END

SPORADIC-ONE-TO-MANY-OBSERVER-DATAVIEW DEFINITIONS ::=
BEGIN

   MyInteger ::= INTEGER (0 .. 10000)

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..3)

   -- List of functions (instances) present in the system
   PID ::= ENUMERATED {
       actuator1,
       
       actuator2,
       
       controller,
       
       
       env
   }

END


Simulation-DataView DEFINITIONS ::=
BEGIN
   IMPORTS
      
      --  ASN.1 modules used by thread actuator1_test_parameter
      MyInteger FROM SPORADIC-ONE-TO-MANY-OBSERVER-DATAVIEW
      
      --  ASN.1 modules used by thread actuator2_test_parameter
      MyInteger FROM SPORADIC-ONE-TO-MANY-OBSERVER-DATAVIEW
      
      
      
      -- Import generic integer type (used for timers)
      T-UInt32 FROM TASTE-BasicTypes
      PID      FROM System-Dataview
      -- Import timers
      AggregateTimerData FROM Simulation-Timers-DataView
      --  Import the SDL function states needed for the global system state
      Actuator1-Context  FROM Actuator1-Datamodel
      Actuator2-Context  FROM Actuator2-Datamodel
      Controller-Context FROM Controller-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Actuator1-Event ::= CHOICE {
      -- Lang: SDL TRUE FALSE
      msg-in CHOICE {
         input-none SEQUENCE {},
         test-parameter SEQUENCE { p1 MyInteger}
      },
      msg-out CHOICE {
         received1 SEQUENCE {   }
      }
   }
   
   Actuator2-Event ::= CHOICE {
      -- Lang: SDL TRUE FALSE
      msg-in CHOICE {
         input-none SEQUENCE {},
         test-parameter SEQUENCE { p1 MyInteger}
      },
      msg-out CHOICE {
         received2 SEQUENCE {   }
      }
   }
   
   Controller-Event ::= CHOICE {
      -- Lang: SDL TRUE FALSE
      msg-in CHOICE {
         input-none SEQUENCE {},
         received1 SEQUENCE {  },
         received2 SEQUENCE {  }
      },
      msg-out CHOICE {
         test-parameter SEQUENCE { p1 MyInteger }
      }
   }
   

   --  Current observer state flag (used by model checkers)
   Observer-State-Kind ::= ENUMERATED {
      regular-state,
      error-state,
      ignore-state,
      success-state
   }

   --  Event related to the execution of a PI or call of a RI in the functional code
   Function-Event ::= CHOICE {
      actuator1  Actuator1-Event,
      actuator2  Actuator2-Event,
      controller Controller-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   actuator1-queue-size INTEGER ::= 2
   actuator2-queue-size INTEGER ::= 2
   controller-queue-size INTEGER ::= 2

   System-State ::= SEQUENCE {
      --  Timers
      timers AggregateTimerData,
      --  Message queues
      actuator1-queue  Events-Ty (SIZE (0 .. actuator1-queue-size)),
      actuator2-queue  Events-Ty (SIZE (0 .. actuator2-queue-size)),
      controller-queue Events-Ty (SIZE (0 .. controller-queue-size)),

      actuator1   Actuator1-Context,
      actuator2   Actuator2-Context,
      controller  Controller-Context
   }


END

Simulation-Timers-DataView DEFINITIONS ::=
BEGIN

   TimerData ::= SEQUENCE {
      timer-enabled BOOLEAN,
      interval INTEGER (0 .. 50000)
   }

   AggregateTimerData ::= SEQUENCE {
      
      
      
      actuator1 SEQUENCE {
      },
      
      actuator2 SEQUENCE {
      },
      
      controller SEQUENCE {
      },
      
      dummy-entry SEQUENCE {}
   }

END
