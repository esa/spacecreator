Left-Datamodel DEFINITIONS ::=
BEGIN
--  This file was generated automatically by OpenGEODE
IMPORTS
   MyInteger FROM INPUTVECTORLIMIT-DATAVIEW
   T-Int32, T-UInt32, T-Int8, T-UInt8, T-Boolean, T-Null-Record FROM TASTE-BasicTypes
   PID-Range, PID FROM System-Dataview;

Left-States ::= ENUMERATED {wait}

Left-Context ::= SEQUENCE {
   state Left-States,
   init-done BOOLEAN,
   sender PID,
   leftarg MyInteger,
   leftval MyInteger
}

END
