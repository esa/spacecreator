FUNCTION-1-SUBTYPE DEFINITIONS ::=
BEGIN

IMPORTS MyChoice FROM CONSTRAINED-RANGE-DATAVIEW


MySeqOf FROM CONSTRAINED-RANGE-DATAVIEW

 ;

MySeqOfSub ::= MySeqOf (SIZE (0..2))

Function-1-pi-1-p1 ::= MySeqOfSub


END
