FUNCTION-1-SUBTYPE DEFINITIONS ::=
BEGIN

IMPORTS MyChoice FROM CHOICE-PRESENT-DATAVIEW


MySeq FROM CHOICE-PRESENT-DATAVIEW

 ;

MySeqSub ::= MySeq (WITH COMPONENTS { inputdata PRESENT })

Function-1-pi-1-p1 ::= MySeqSub

END
