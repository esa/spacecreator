FUNCTION-1-SUBTYPE DEFINITIONS ::=
BEGIN

IMPORTS MySeq FROM BASIC-PRESENT-DATAVIEW


MyChoice FROM BASIC-PRESENT-DATAVIEW


 ;

MySeqSub ::= MySeq (WITH COMPONENTS { inputdata PRESENT })

Function-1-pi-1-p1 ::= MySeqSub




END
