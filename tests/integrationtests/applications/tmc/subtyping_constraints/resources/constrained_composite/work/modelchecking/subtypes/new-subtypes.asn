FUNCTION-1-SUBTYPE DEFINITIONS ::=
BEGIN

IMPORTS MySeqOf FROM CONSTRAINED-COMPOSITE-DATAVIEW


MyChoice FROM CONSTRAINED-COMPOSITE-DATAVIEW

 ;




Function-1-pi-2-p1 ::= MySeqOf (SIZE(0..2))




Function-1-pi-1-p1 ::= MyChoice




END
