FUNCTION-1-SUBTYPE DEFINITIONS ::=
BEGIN

IMPORTS MySeqOf FROM COMPOSITE-DATAVIEW


MyChoice FROM COMPOSITE-DATAVIEW

 ;




Function-1-pi-2-p1 ::= MySeqOf




Function-1-pi-1-p1 ::= MyChoice




END
