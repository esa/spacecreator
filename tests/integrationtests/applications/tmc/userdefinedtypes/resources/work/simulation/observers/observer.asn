Receiver-Datamodel DEFINITIONS ::=
BEGIN
IMPORTS
   T-Int32, T-UInt32, T-Int8, T-UInt8, T-Boolean, T-Null-Record FROM TASTE-BasicTypes
   MyInteger, MyBetterInteger, MyBool, MyBetterBoolean FROM USERDEFINED-TYPES-DATAVIEW;

Receiver-States ::= ENUMERATED {wait}

Receiver-Context ::= SEQUENCE {
   state Receiver-States,
   init-done BOOLEAN,
   integerarg MyBetterInteger,
   integervalue MyBetterInteger,
   integerhandled T-Boolean,
   boolarg MyBetterBoolean,
   boolvalue MyBetterBoolean,
   boolhandled T-Boolean
}

END

TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


USERDEFINED-TYPES-DATAVIEW DEFINITIONS ::=
BEGIN

    MyInteger ::= INTEGER (0 .. 10)
    MyBetterInteger ::= MyInteger (2 .. 5)

    MyBool ::= BOOLEAN
    MyBetterBoolean ::= MyBool
END



Simulation-DataView DEFINITIONS ::=
BEGIN
   IMPORTS
      
      
      --  ASN.1 modules used by thread receiver_BoolInterface
      MyBetterBoolean FROM USERDEFINED-TYPES-DATAVIEW
      
      --  ASN.1 modules used by thread receiver_IntegerInterface
      MyBetterInteger FROM USERDEFINED-TYPES-DATAVIEW
      
      -- Import generic integer type (used for timers)
      T-UInt32 FROM TASTE-BasicTypes
      --  Import the SDL function states needed for the global system state
      Receiver-Context FROM Receiver-Datamodel
   ;

   --  List all the TASTE functions present in the system
   PID ::= ENUMERATED {
        env, pinger, receiver
   }

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Pinger-Event ::= CHOICE {
      msg-out CHOICE {
         boolinterface    SEQUENCE { boolarg MyBetterBoolean },
         integerinterface SEQUENCE { integerarg MyBetterInteger }
      }
   }
   
   Receiver-Event ::= CHOICE {
      msg-in CHOICE {
         input-none SEQUENCE {},
         boolinterface    SEQUENCE { boolarg MyBetterBoolean},
         integerinterface SEQUENCE { integerarg MyBetterInteger}
      }
   }
   

   --  Current observer state flag (used by model checkers)
   Observer-State-Kind ::= ENUMERATED {
      regular-state,
      error-state,
      ignore-state,
      success-state
   }

   --  Event related to the execution of a PI or call of a RI in the functional code
   Function-Event ::= CHOICE {
      pinger   Pinger-Event,
      receiver Receiver-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event    --  message received in a state where it is not expected
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   receiver-queue-size INTEGER ::= 2
   System-State ::= SEQUENCE {
      --  Message queues
      receiver-queue Events-Ty (SIZE (0 .. receiver-queue-size)),

      receiver  Receiver-Context
   }

END
