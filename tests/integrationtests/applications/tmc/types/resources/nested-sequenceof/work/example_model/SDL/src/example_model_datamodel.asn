Example-model-Datamodel DEFINITIONS ::=
BEGIN
--  This file was generated automatically by OpenGEODE
IMPORTS
   MyInteger, LowSequenceOf, HighSequenceOf FROM NESTED-SEQUENCEOF-DATAVIEW
   T-Int32, T-UInt32, T-Int8, T-UInt8, T-Boolean, T-Null-Record, T-Runtime-Error FROM TASTE-BasicTypes
   PID-Range, PID FROM System-Dataview;

Example-model-States ::= ENUMERATED {wait}

Example-model-Context ::= SEQUENCE {
   state Example-model-States,
   init-done BOOLEAN,
   sender PID,
   offspring PID,
   param HighSequenceOf
}

Example-Model-T-Runtime-Error-Selection ::= ENUMERATED {noerror-present(1), encodeerror-present(2), decodeerror-present(3)}
END
