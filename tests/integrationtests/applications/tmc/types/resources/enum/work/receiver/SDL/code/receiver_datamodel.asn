Receiver-Datamodel DEFINITIONS ::=
BEGIN
IMPORTS
   T-Int32, T-UInt32, T-Int8, T-UInt8, T-Boolean, T-Null-Record FROM TASTE-BasicTypes
   MyEnum, MyBetterEnum FROM USERDEFINED-TYPES-DATAVIEW;

Receiver-States ::= ENUMERATED {wait}

Receiver-Context ::= SEQUENCE {
   state Receiver-States,
   init-done BOOLEAN,
   enumarg MyBetterEnum,
   enumvalue MyBetterEnum,
   enumhandled T-Boolean
}

END
