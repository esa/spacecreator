Receiver-Datamodel DEFINITIONS ::=
BEGIN
--  This file was generated automatically by OpenGEODE
IMPORTS
   T-Int32, T-UInt32, T-Int8, T-UInt8, T-Boolean, T-Null-Record FROM TASTE-BasicTypes
   MyChoice, MyBetterChoice FROM USERDEFINED-TYPES-DATAVIEW
   PID-Range, PID FROM System-Dataview;

Receiver-States ::= ENUMERATED {wait}

Receiver-Context ::= SEQUENCE {
   state Receiver-States,
   init-done BOOLEAN,
   sender PID,
   offspring PID,
   choicearg MyBetterChoice,
   choicevalue MyBetterChoice,
   choicehandled T-Boolean
}

Receiver-Mychoice-Selection ::= ENUMERATED {option1-present(1), option2-present(2)}
END
