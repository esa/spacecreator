Receiver-Datamodel DEFINITIONS ::=
BEGIN
IMPORTS
   T-Int32, T-UInt32, T-Int8, T-UInt8, T-Boolean, T-Null-Record FROM TASTE-BasicTypes
   MyInteger, MyBetterInteger FROM USERDEFINED-TYPES-DATAVIEW;

Receiver-States ::= ENUMERATED {wait}

Receiver-Context ::= SEQUENCE {
   state Receiver-States,
   init-done BOOLEAN,
   integerarg MyBetterInteger,
   integervalue MyBetterInteger,
   integerhandled T-Boolean
}

END
