Controller-Datamodel DEFINITIONS ::=
BEGIN
--  This file was generated automatically by OpenGEODE
IMPORTS
   MyInteger, MyReal FROM GUIPROJECT-DATAVIEW
   T-Int32, T-UInt32, T-Int8, T-UInt8, T-Boolean, T-Null-Record FROM TASTE-BasicTypes
   PID-Range, PID FROM System-Dataview;

Controller-States ::= ENUMERATED {wait, finish, failure}

Controller-Context ::= SEQUENCE {
   state Controller-States,
   init-done BOOLEAN,
   sender PID,
   offspring PID,
   param MyReal
}

END
