IA5STRING-DATAVIEW DEFINITIONS ::=
BEGIN

    MyString ::= IA5String (SIZE(1))
    MyBetterString ::= MyString

END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


-- Dataview generated on-the-fly providing information on the system
-- and made available to the user code.
System-Dataview DEFINITIONS ::=
BEGIN

   -- Range of PID - type can be used to size arrays of PID type
   PID-Range ::= INTEGER(0..2)

   -- List of functions (instances) present in the system
   PID ::= ENUMERATED {
       pinger,
       
       receiver,
       
       
       env
   }

END
