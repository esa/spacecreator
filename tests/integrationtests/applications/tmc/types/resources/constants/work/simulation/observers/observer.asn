Black-hole-Datamodel DEFINITIONS ::=
BEGIN
--  This file was generated automatically by OpenGEODE
IMPORTS
   MyInteger, MyComplexA, MyBoolean, MyOctetString, MyIA5String, MyEnumerated, MyChoice, MySequence, MyInlineSequence, MySequenceOf FROM CONSTANTS-DATAVIEW
   T-Int32, T-UInt32, T-Int8, T-UInt8, T-Boolean, T-Null-Record, T-Runtime-Error FROM TASTE-BasicTypes
   PID-Range, PID FROM System-Dataview;

Black-hole-States ::= ENUMERATED {wait}

Black-hole-Context ::= SEQUENCE {
   state Black-hole-States,
   init-done BOOLEAN,
   sender PID,
   offspring PID
}

Black-Hole-Mychoice-Selection ::= ENUMERATED {scenario-a-present(1), scenario-b-present(2)}
Black-Hole-T-Runtime-Error-Selection ::= ENUMERATED {noerror-present(1), encodeerror-present(2), decodeerror-present(3)}
END

CONSTANTS-DATAVIEW DEFINITIONS ::=
BEGIN

   MyInteger ::= INTEGER (0 .. 10)

   MyComplexA ::= SEQUENCE {
     example-a MyInteger,
     example-b MyInteger OPTIONAL
   }

   MyBoolean ::= BOOLEAN
   MyOctetString ::= OCTET STRING (SIZE(4))
   MyIA5String ::= IA5String (SIZE(4))
   MyEnumerated ::= ENUMERATED {
      option-a, option-b, option-c
   }
   MyChoice ::= CHOICE {
      scenario-a MyInteger,
      scenario-b MyComplexA
   }
   MySequence ::= SEQUENCE {
      subsystem-a MyInteger,
      subsystem-b MyComplexA
   }
   MyInlineSequence ::= SEQUENCE {
      configuration-a SEQUENCE { param-a INTEGER (0 .. 100), param-b INTEGER (1 .. 32) },
      configuration-b MyInteger
   }
   MySequenceOf ::= SEQUENCE (SIZE(2)) OF MyComplexA


   test-int MyInteger ::= 4
   test-bool MyBoolean ::= TRUE
   test-octet-string MyOctetString ::= 'aabbccdd'H
   test-ia5-string MyIA5String ::= "beta"
   test-enumerated MyEnumerated ::= option-b
   test-choice MyChoice ::= scenario-b : { example-a 8, example-b 4 }
   test-sequence MySequence ::= {
      subsystem-a 1,
      subsystem-b { example-a 2, example-b 4 }
   }
   test-inline-sequence MyInlineSequence ::= {
      configuration-a { param-a 0, param-b 2 },
      configuration-b 4
   }
   test-sequence-of MySequenceOf ::= {
      { example-a 1 },
      { example-a 2, example-b 4 }
   }
END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

T-Runtime-Error ::= CHOICE {
   noerror T-UInt32, -- this shall be NULL, but DMT does not support NULL and SEDS does not support empty sequences
   encodeerror T-Int32, -- the names shall be changed after fix in seds converter (space creator) will be merged
   decodeerror T-Int32
}

END

-- Dataview generated on-the-fly providing information on the system
-- and made available to the user code.
System-Dataview DEFINITIONS ::=
BEGIN

   -- Range of PID - type can be used to size arrays of PID type
   PID-Range ::= INTEGER(0..2)

   -- List of functions (instances) present in the system
   PID ::= ENUMERATED {
       black-hole,
       
       environ,
       
       
       env
   }

END

ENVIRON-SUBTYPE DEFINITIONS ::=
BEGIN

IMPORTS 

MyInteger FROM CONSTANTS-DATAVIEW

 ;







Environ-write-data-p1 ::= MyInteger




END


Simulation-DataView DEFINITIONS ::=
BEGIN
   IMPORTS
      
      --  ASN.1 modules used by thread black_hole_write_data
      MyInteger FROM CONSTANTS-DATAVIEW
      
      
      -- Import generic integer type (used for timers)
      T-UInt32 FROM TASTE-BasicTypes
      PID      FROM System-Dataview
      -- Import timers
      AggregateTimerData FROM Simulation-Timers-DataView
      --  Import the SDL function states needed for the global system state
      Black-hole-Context FROM Black-hole-Datamodel
   ;

   --  Simulator needs to knows about cyclic interfaces
   Periodic-Event {Event-Ty} ::= SEQUENCE {
      period INTEGER (0 .. 500000),  -- Upper limit is arbitrary
      event  Event-Ty
   }

   --  To keep a constant list of events.
   Periodic-Events {Event-Ty, INTEGER:max} ::=
      SEQUENCE (SIZE (0 .. max)) OF Periodic-Event {Event-Ty}

   
   
   
   Black-Hole-Event ::= CHOICE {
      msg-in CHOICE {
         input-none SEQUENCE {},
         write-data SEQUENCE { p1 MyInteger}
      }
   }
   
   Environ-Event ::= CHOICE {
      msg-out CHOICE {
         write-data SEQUENCE { p1 MyInteger }
      }
   }
   

   --  Current observer state flag (used by model checkers)
   Observer-State-Kind ::= ENUMERATED {
      regular-state,
      error-state,
      ignore-state,
      success-state
   }

   --  Event related to the execution of a PI or call of a RI in the functional code
   Function-Event ::= CHOICE {
      black-hole Black-Hole-Event,
      environ    Environ-Event
   }

   --  Type used to store events in a database: associate a name to the event
   Named-Function-Event ::= SEQUENCE {
      id    IA5String (SIZE (1..80)),
      event Function-Event
   }

   --  Event at interface level (PI or RI), including source and destination ID
   Interface-Event ::= SEQUENCE {
      source PID,
      dest   PID,
      event  Function-Event
   }

   --  Event generated when a function uses the CREATE symbol to start an instance
   Create-Event  ::= SEQUENCE {
      source PID,  --  parent
      dest   PID   --  offspring
   }

   -- Event generated when a previously CREATed instance terminates
   Delete-Event ::= SEQUENCE {
      instance PID
   }

   --  Event sent to the observers
   Observable-Event ::= CHOICE {
      no-event        SEQUENCE {},
      system-startup  SEQUENCE {},
      input-event     Interface-Event,   --  input event is evaluated after the transition
      output-event    Interface-Event,   --  output event is evaluated before the message is sent
      unhandled-input Interface-Event,   --  message received in a state where it is not expected
      create-instance Create-Event,      --  sent after the instance creation
      delete-instance Delete-Event
   }

   --  constant that can be used to refer to the absence of an input/output event
   nothing Observable-Event ::= no-event : {}

   --  Define a queue of events, corresponding to the input queue for each function
   max-events INTEGER ::= 10
   Events-Ty ::= SEQUENCE (SIZE (0 .. max-events)) OF Observable-Event

   --  Global system state (excluding observers, which are defined later)
   black-hole-queue-size INTEGER ::= 2

   System-State ::= SEQUENCE {
      --  Timers
      timers AggregateTimerData,
      --  Message queues
      black-hole-queue Events-Ty (SIZE (0 .. black-hole-queue-size)),

      black-hole  Black-hole-Context
   }

   --  List the GUI functions (environment of the system being simulated)
   System-GUIs ::= ENUMERATED {
      environ
   }

END

Simulation-Timers-DataView DEFINITIONS ::=
BEGIN

   TimerData ::= SEQUENCE {
      timer-enabled BOOLEAN,
      interval INTEGER (0 .. 50000)
   }

   AggregateTimerData ::= SEQUENCE {
      
      
      
      black-hole SEQUENCE {
      },
      
      dummy-entry SEQUENCE {}
   }

END
