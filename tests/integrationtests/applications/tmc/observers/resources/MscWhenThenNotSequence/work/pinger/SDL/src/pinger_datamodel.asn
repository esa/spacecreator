Pinger-Datamodel DEFINITIONS ::=
BEGIN
--  This file was generated automatically by OpenGEODE
IMPORTS
   MyInteger FROM MSCWHENTHENSEQUENCE-DATAVIEW
   T-Int32, T-UInt32, T-Int8, T-UInt8, T-Boolean, T-Null-Record FROM TASTE-BasicTypes
   PID-Range, PID FROM System-Dataview;

Pinger-States ::= ENUMERATED {wait, help}

Pinger-Context ::= SEQUENCE {
   state Pinger-States,
   init-done BOOLEAN,
   sender PID,
   offspring PID
}

END
