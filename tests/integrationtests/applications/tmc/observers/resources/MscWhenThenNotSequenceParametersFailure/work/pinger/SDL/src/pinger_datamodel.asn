Pinger-Datamodel DEFINITIONS ::=
BEGIN
--  This file was generated automatically by OpenGEODE
IMPORTS
   SmallInteger, BigInteger, MyChoice, MySequence FROM MSCWHENTHENNOTSEQUENCEPARAMETERSFAILURE-DATAVIEW
   T-Int32, T-UInt32, T-Int8, T-UInt8, T-Boolean, T-Null-Record FROM TASTE-BasicTypes
   PID-Range, PID FROM System-Dataview;

Pinger-States ::= ENUMERATED {ok1, wait, ok2}

Pinger-Context ::= SEQUENCE {
   state Pinger-States,
   init-done BOOLEAN,
   sender PID,
   offspring PID,
   value1 MySequence,
   value2 MySequence
}

Pinger-Mychoice-Selection ::= ENUMERATED {small-present(1), big-present(2)}
END
