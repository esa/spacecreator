Model-Datamodel DEFINITIONS ::=
BEGIN
--  This file was generated automatically by OpenGEODE
IMPORTS
   MyInteger, MyIntegerBigger FROM INPUTMONITORING-DATAVIEW
   T-Int32, T-UInt32, T-Int8, T-UInt8, T-Boolean, T-Null-Record FROM TASTE-BasicTypes
   PID-Range, PID FROM System-Dataview;

Model-States ::= ENUMERATED {s1}

Model-Context ::= SEQUENCE {
   state Model-States,
   init-done BOOLEAN,
   sender PID,
   offspring PID,
   x MyInteger,
   y MyIntegerBigger
}

END
