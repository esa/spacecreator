Model-Datamodel DEFINITIONS ::=
BEGIN
IMPORTS
   MyInteger, MyIntegerBigger FROM INPUTMONITORING-DATAVIEW
   T-Int32, T-UInt32, T-Int8, T-UInt8, T-Boolean, T-Null-Record FROM TASTE-BasicTypes;

Model-States ::= ENUMERATED {s1}

Model-Context ::= SEQUENCE {
   state Model-States,
   init-done BOOLEAN,
   x MyInteger,
   y MyIntegerBigger
}

END
