Helper-Datamodel DEFINITIONS ::=
BEGIN
--  This file was generated automatically by OpenGEODE
IMPORTS
   MyInteger FROM MSCOBSERVER-DATAVIEW
   T-Int32, T-UInt32, T-Int8, T-UInt8, T-Boolean, T-Null-Record FROM TASTE-BasicTypes
   PID-Range, PID FROM System-Dataview;

Helper-States ::= ENUMERATED {wait}

Helper-Context ::= SEQUENCE {
   state Helper-States,
   init-done BOOLEAN,
   sender PID,
   offspring PID
}

END
