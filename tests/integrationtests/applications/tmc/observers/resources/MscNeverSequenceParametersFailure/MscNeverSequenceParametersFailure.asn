MSCNEVERSEQUENCEPARAMETERSFAILURE-DATAVIEW DEFINITIONS ::=
BEGIN

    SmallInteger ::= INTEGER (0 .. 2)
    BigInteger ::= INTEGER (3 .. 5)
    SeqOfSmall ::= SEQUENCE (SIZE(1)) OF SmallInteger
    SeqOfBig ::= SEQUENCE (SIZE(1)) OF BigInteger
    MyChoice ::= CHOICE {
       small SeqOfSmall,
       big SeqOfBig
    }
    My-Sequence ::= SEQUENCE {
       value SmallInteger,
       version MyChoice
    }

END
