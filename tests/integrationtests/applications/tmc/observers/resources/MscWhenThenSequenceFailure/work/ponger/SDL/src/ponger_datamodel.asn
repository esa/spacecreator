Ponger-Datamodel DEFINITIONS ::=
BEGIN
--  This file was generated automatically by OpenGEODE
IMPORTS
   MyInteger FROM MSCWHENTHENSEQUENCE-DATAVIEW
   T-Int32, T-UInt32, T-Int8, T-UInt8, T-Boolean, T-Null-Record FROM TASTE-BasicTypes
   PID-Range, PID FROM System-Dataview;

Ponger-States ::= ENUMERATED {help, wait}

Ponger-Context ::= SEQUENCE {
   state Ponger-States,
   init-done BOOLEAN,
   sender PID
}

END
