INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
BoolSimulinkIntEnumType ::= ENUMERATED
{
    no(-1),
    yes(1)
}
BoolUInt8Enum ::= ENUMERATED
{
    no(0),
    yes(1)
}
BoolUInt16Enum ::= ENUMERATED
{
    no(0),
    yes(1)
}
BoolInt8Enum ::= ENUMERATED
{
    no(-1),
    yes(1)
}
BoolInt16Enum ::= ENUMERATED
{
    no(-1),
    yes(1)
}
BoolInt32Enum ::= ENUMERATED
{
    no(-1),
    yes(1)
}
BusDef ::= SEQUENCE 
{ 
    boolSimulinkIntEnumTypeMember SEQUENCE (SIZE(2)) OF SEQUENCE (SIZE(2)) OF BoolSimulinkIntEnumType, 
    boolUInt8EnumMember SEQUENCE (SIZE(2)) OF SEQUENCE (SIZE(2)) OF BoolUInt8Enum, 
    boolUInt16EnumMember SEQUENCE (SIZE(2)) OF SEQUENCE (SIZE(2)) OF BoolUInt16Enum, 
    boolInt8EnumMember SEQUENCE (SIZE(2)) OF SEQUENCE (SIZE(2)) OF BoolInt8Enum, 
    boolInt16EnumMember SEQUENCE (SIZE(2)) OF SEQUENCE (SIZE(2)) OF BoolInt16Enum, 
    boolInt32EnumMember SEQUENCE (SIZE(2)) OF SEQUENCE (SIZE(2)) OF BoolInt32Enum
} 
END
