INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
I1-Type ::= SEQUENCE (SIZE(2)) OF MatLab-Double
I2-Type ::= SEQUENCE (SIZE(2)) OF MatLab-Single
I3-Type ::= SEQUENCE (SIZE(2)) OF MatLab-Int8
I4-Type ::= SEQUENCE (SIZE(2)) OF MatLab-Uint8
I5-Type ::= SEQUENCE (SIZE(2)) OF MatLab-Int16
I6-Type ::= SEQUENCE (SIZE(2)) OF MatLab-Uint16
I7-Type ::= SEQUENCE (SIZE(2)) OF MatLab-Int32
I8-Type ::= SEQUENCE (SIZE(2)) OF MatLab-Uint32
I9-Type ::= SEQUENCE (SIZE(2)) OF MatLab-Boolean
O1-Type ::= SEQUENCE (SIZE(2)) OF MatLab-Double
O2-Type ::= SEQUENCE (SIZE(2)) OF MatLab-Single
O3-Type ::= SEQUENCE (SIZE(2)) OF MatLab-Int8
O4-Type ::= SEQUENCE (SIZE(2)) OF MatLab-Uint8
O5-Type ::= SEQUENCE (SIZE(2)) OF MatLab-Int16
O6-Type ::= SEQUENCE (SIZE(2)) OF MatLab-Uint16
O7-Type ::= SEQUENCE (SIZE(2)) OF MatLab-Int32
O8-Type ::= SEQUENCE (SIZE(2)) OF MatLab-Uint32
O9-Type ::= SEQUENCE (SIZE(2)) OF MatLab-Boolean
END
