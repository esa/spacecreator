INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
AliasBoolean ::= MatLab-Boolean
AliasDouble ::= MatLab-Double
AliasInt16 ::= MatLab-Int16
AliasInt32 ::= MatLab-Int32
AliasInt8 ::= MatLab-Int8
AliasSingle ::= MatLab-Single
AliasToAliasBoolean ::= AliasBoolean
AliasToAliasDouble ::= AliasDouble
AliasToAliasInt16 ::= AliasInt16
AliasToAliasInt32 ::= AliasInt32
AliasToAliasInt8 ::= AliasInt8
AliasToAliasSingle ::= AliasSingle
AliasUInt16 ::= MatLab-Uint16
AliasToAliasUInt16 ::= AliasUInt16
AliasUInt32 ::= MatLab-Uint32
AliasToAliasUInt32 ::= AliasUInt32
AliasUInt8 ::= MatLab-Uint8
AliasToAliasUInt8 ::= AliasUInt8
END
