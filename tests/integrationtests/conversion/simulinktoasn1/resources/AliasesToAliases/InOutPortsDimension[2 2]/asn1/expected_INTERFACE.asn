INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
AliasBoolean ::= MatLab-Boolean
AliasDouble ::= MatLab-Double
AliasInt16 ::= MatLab-Int16
AliasInt32 ::= MatLab-Int32
AliasInt8 ::= MatLab-Int8
AliasSingle ::= MatLab-Single
AliasToAliasBoolean ::= AliasBoolean
AliasToAliasDouble ::= AliasDouble
AliasToAliasInt16 ::= AliasInt16
AliasToAliasInt32 ::= AliasInt32
AliasToAliasInt8 ::= AliasInt8
AliasToAliasSingle ::= AliasSingle
AliasUInt16 ::= MatLab-Uint16
AliasToAliasUInt16 ::= AliasUInt16
AliasUInt32 ::= MatLab-Uint32
AliasToAliasUInt32 ::= AliasUInt32
AliasUInt8 ::= MatLab-Uint8
AliasToAliasUInt8 ::= AliasUInt8
I1-Type ::= SEQUENCE (SIZE(2)) OF SEQUENCE (SIZE(2)) OF AliasToAliasDouble
I2-Type ::= SEQUENCE (SIZE(2)) OF SEQUENCE (SIZE(2)) OF AliasToAliasSingle
I3-Type ::= SEQUENCE (SIZE(2)) OF SEQUENCE (SIZE(2)) OF AliasToAliasInt8
I4-Type ::= SEQUENCE (SIZE(2)) OF SEQUENCE (SIZE(2)) OF AliasToAliasUInt8
I5-Type ::= SEQUENCE (SIZE(2)) OF SEQUENCE (SIZE(2)) OF AliasToAliasInt16
I6-Type ::= SEQUENCE (SIZE(2)) OF SEQUENCE (SIZE(2)) OF AliasToAliasUInt16
I7-Type ::= SEQUENCE (SIZE(2)) OF SEQUENCE (SIZE(2)) OF AliasToAliasInt32
I8-Type ::= SEQUENCE (SIZE(2)) OF SEQUENCE (SIZE(2)) OF AliasToAliasUInt32
I9-Type ::= SEQUENCE (SIZE(2)) OF SEQUENCE (SIZE(2)) OF AliasToAliasBoolean
O1-Type ::= SEQUENCE (SIZE(2)) OF SEQUENCE (SIZE(2)) OF AliasToAliasDouble
O2-Type ::= SEQUENCE (SIZE(2)) OF SEQUENCE (SIZE(2)) OF AliasToAliasSingle
O3-Type ::= SEQUENCE (SIZE(2)) OF SEQUENCE (SIZE(2)) OF AliasToAliasInt8
O4-Type ::= SEQUENCE (SIZE(2)) OF SEQUENCE (SIZE(2)) OF AliasToAliasUInt8
O5-Type ::= SEQUENCE (SIZE(2)) OF SEQUENCE (SIZE(2)) OF AliasToAliasInt16
O6-Type ::= SEQUENCE (SIZE(2)) OF SEQUENCE (SIZE(2)) OF AliasToAliasUInt16
O7-Type ::= SEQUENCE (SIZE(2)) OF SEQUENCE (SIZE(2)) OF AliasToAliasInt32
O8-Type ::= SEQUENCE (SIZE(2)) OF SEQUENCE (SIZE(2)) OF AliasToAliasUInt32
O9-Type ::= SEQUENCE (SIZE(2)) OF SEQUENCE (SIZE(2)) OF AliasToAliasBoolean
END
