INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
BusDef ::= SEQUENCE 
{ 
    doubleMember SEQUENCE (SIZE(2)) OF SEQUENCE (SIZE(2)) OF MatLab-Double, 
    singleMember SEQUENCE (SIZE(2)) OF SEQUENCE (SIZE(2)) OF MatLab-Single, 
    int8Member SEQUENCE (SIZE(2)) OF SEQUENCE (SIZE(2)) OF MatLab-Int8, 
    uint8Member SEQUENCE (SIZE(2)) OF SEQUENCE (SIZE(2)) OF MatLab-Uint8, 
    int16Member SEQUENCE (SIZE(2)) OF SEQUENCE (SIZE(2)) OF MatLab-Int16, 
    uint16Member SEQUENCE (SIZE(2)) OF SEQUENCE (SIZE(2)) OF MatLab-Uint16, 
    int32Member SEQUENCE (SIZE(2)) OF SEQUENCE (SIZE(2)) OF MatLab-Int32, 
    uint32Member SEQUENCE (SIZE(2)) OF SEQUENCE (SIZE(2)) OF MatLab-Uint32, 
    booleanMember SEQUENCE (SIZE(2)) OF SEQUENCE (SIZE(2)) OF MatLab-Boolean
} 
END
