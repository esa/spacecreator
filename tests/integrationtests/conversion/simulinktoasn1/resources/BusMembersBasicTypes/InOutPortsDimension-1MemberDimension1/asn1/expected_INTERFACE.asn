INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
BusDef ::= SEQUENCE 
{ 
    doubleMember MatLab-Double, 
    singleMember MatLab-Single, 
    int8Member MatLab-Int8, 
    uint8Member MatLab-Uint8, 
    int16Member MatLab-Int16, 
    uint16Member MatLab-Uint16, 
    int32Member MatLab-Int32, 
    uint32Member MatLab-Uint32, 
    booleanMember MatLab-Boolean
} 
END
