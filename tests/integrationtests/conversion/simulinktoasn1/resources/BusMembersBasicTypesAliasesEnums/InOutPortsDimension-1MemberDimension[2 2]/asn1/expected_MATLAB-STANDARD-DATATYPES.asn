MATLAB-STANDARD-DATATYPES DEFINITIONS ::= BEGIN
MatLab-Boolean ::= BOOLEAN
MatLab-Double ::= REAL(-1.79769e+308 .. 1.79769e+308)
MatLab-Single ::= REAL(-3.40282e+38 .. 3.40282e+38)
MatLab-Int8 ::= INTEGER(-128 .. 127)
MatLab-Uint8 ::= INTEGER(0 .. 255)
MatLab-Int16 ::= INTEGER(-32768 .. 32767)
MatLab-Uint16 ::= INTEGER(0 .. 65535)
MatLab-Int32 ::= INTEGER(-2147483648 .. 2147483647)
MatLab-Uint32 ::= INTEGER(0 .. 4294967295)
END
