INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
AliasBoolean ::= MatLab-Boolean
AliasDouble ::= MatLab-Double
AliasInt16 ::= MatLab-Int16
AliasInt32 ::= MatLab-Int32
AliasInt8 ::= MatLab-Int8
AliasSingle ::= MatLab-Single
AliasUInt16 ::= MatLab-Uint16
AliasUInt32 ::= MatLab-Uint32
AliasUInt8 ::= MatLab-Uint8
BusAliasesToStandardTypesDef ::= SEQUENCE 
{ 
    aliasBooleanMember SEQUENCE (SIZE(2)) OF SEQUENCE (SIZE(2)) OF AliasBoolean, 
    aliasDoubleMember SEQUENCE (SIZE(2)) OF SEQUENCE (SIZE(2)) OF AliasDouble, 
    aliasSingleMember SEQUENCE (SIZE(2)) OF SEQUENCE (SIZE(2)) OF AliasSingle, 
    aliasInt8Member SEQUENCE (SIZE(2)) OF SEQUENCE (SIZE(2)) OF AliasInt8, 
    aliasInt16Member SEQUENCE (SIZE(2)) OF SEQUENCE (SIZE(2)) OF AliasInt16, 
    aliasInt32Member SEQUENCE (SIZE(2)) OF SEQUENCE (SIZE(2)) OF AliasInt32, 
    aliasUInt8Member SEQUENCE (SIZE(2)) OF SEQUENCE (SIZE(2)) OF AliasUInt8, 
    aliasUInt16Member SEQUENCE (SIZE(2)) OF SEQUENCE (SIZE(2)) OF AliasUInt16, 
    aliasUInt32Member SEQUENCE (SIZE(2)) OF SEQUENCE (SIZE(2)) OF AliasUInt32
} 
BusStandardTypesDef ::= SEQUENCE 
{ 
    doubleMember SEQUENCE (SIZE(2)) OF SEQUENCE (SIZE(2)) OF MatLab-Double, 
    singleMember SEQUENCE (SIZE(2)) OF SEQUENCE (SIZE(2)) OF MatLab-Single, 
    int8Member SEQUENCE (SIZE(2)) OF SEQUENCE (SIZE(2)) OF MatLab-Int8, 
    uint8Member SEQUENCE (SIZE(2)) OF SEQUENCE (SIZE(2)) OF MatLab-Uint8, 
    int16Member SEQUENCE (SIZE(2)) OF SEQUENCE (SIZE(2)) OF MatLab-Int16, 
    uint16Member SEQUENCE (SIZE(2)) OF SEQUENCE (SIZE(2)) OF MatLab-Uint16, 
    int32Member SEQUENCE (SIZE(2)) OF SEQUENCE (SIZE(2)) OF MatLab-Int32, 
    uint32Member SEQUENCE (SIZE(2)) OF SEQUENCE (SIZE(2)) OF MatLab-Uint32, 
    booleanMember SEQUENCE (SIZE(2)) OF SEQUENCE (SIZE(2)) OF MatLab-Boolean
} 
BoolSimulinkIntEnumType ::= ENUMERATED
{
    no(-1),
    yes(1)
}
BoolUInt8Enum ::= ENUMERATED
{
    no(0),
    yes(1)
}
BoolUInt16Enum ::= ENUMERATED
{
    no(0),
    yes(1)
}
BoolInt8Enum ::= ENUMERATED
{
    no(-1),
    yes(1)
}
BoolInt16Enum ::= ENUMERATED
{
    no(-1),
    yes(1)
}
BoolInt32Enum ::= ENUMERATED
{
    no(-1),
    yes(1)
}
BusEnumsDef ::= SEQUENCE 
{ 
    boolSimulinkIntEnumTypeMember SEQUENCE (SIZE(2)) OF SEQUENCE (SIZE(2)) OF BoolSimulinkIntEnumType, 
    boolUInt8EnumMember SEQUENCE (SIZE(2)) OF SEQUENCE (SIZE(2)) OF BoolUInt8Enum, 
    boolUInt16EnumMember SEQUENCE (SIZE(2)) OF SEQUENCE (SIZE(2)) OF BoolUInt16Enum, 
    boolInt8EnumMember SEQUENCE (SIZE(2)) OF SEQUENCE (SIZE(2)) OF BoolInt8Enum, 
    boolInt16EnumMember SEQUENCE (SIZE(2)) OF SEQUENCE (SIZE(2)) OF BoolInt16Enum, 
    boolInt32EnumMember SEQUENCE (SIZE(2)) OF SEQUENCE (SIZE(2)) OF BoolInt32Enum
} 
BusDef ::= SEQUENCE 
{ 
    busStandardTypesDefMember SEQUENCE (SIZE(2)) OF SEQUENCE (SIZE(2)) OF BusStandardTypesDef, 
    busAliasesToStandardTypesDefMember SEQUENCE (SIZE(2)) OF SEQUENCE (SIZE(2)) OF BusAliasesToStandardTypesDef, 
    busEnumsDefMember SEQUENCE (SIZE(2)) OF SEQUENCE (SIZE(2)) OF BusEnumsDef
} 
END
