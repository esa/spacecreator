INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
AliasBoolean ::= MatLab-Boolean
AliasDouble ::= MatLab-Double
AliasInt16 ::= MatLab-Int16
AliasInt32 ::= MatLab-Int32
AliasInt8 ::= MatLab-Int8
AliasSingle ::= MatLab-Single
AliasUInt16 ::= MatLab-Uint16
AliasUInt32 ::= MatLab-Uint32
AliasUInt8 ::= MatLab-Uint8
BusAliasesToStandardTypesDef ::= SEQUENCE 
{ 
    aliasBooleanMember AliasBoolean, 
    aliasDoubleMember AliasDouble, 
    aliasSingleMember AliasSingle, 
    aliasInt8Member AliasInt8, 
    aliasInt16Member AliasInt16, 
    aliasInt32Member AliasInt32, 
    aliasUInt8Member AliasUInt8, 
    aliasUInt16Member AliasUInt16, 
    aliasUInt32Member AliasUInt32
} 
BusStandardTypesDef ::= SEQUENCE 
{ 
    doubleMember MatLab-Double, 
    singleMember MatLab-Single, 
    int8Member MatLab-Int8, 
    uint8Member MatLab-Uint8, 
    int16Member MatLab-Int16, 
    uint16Member MatLab-Uint16, 
    int32Member MatLab-Int32, 
    uint32Member MatLab-Uint32, 
    booleanMember MatLab-Boolean
} 
BoolSimulinkIntEnumType ::= ENUMERATED
{
    no(-1),
    yes(1)
}
BoolUInt8Enum ::= ENUMERATED
{
    no(0),
    yes(1)
}
BoolUInt16Enum ::= ENUMERATED
{
    no(0),
    yes(1)
}
BoolInt8Enum ::= ENUMERATED
{
    no(-1),
    yes(1)
}
BoolInt16Enum ::= ENUMERATED
{
    no(-1),
    yes(1)
}
BoolInt32Enum ::= ENUMERATED
{
    no(-1),
    yes(1)
}
BusEnumsDef ::= SEQUENCE 
{ 
    boolSimulinkIntEnumTypeMember BoolSimulinkIntEnumType, 
    boolUInt8EnumMember BoolUInt8Enum, 
    boolUInt16EnumMember BoolUInt16Enum, 
    boolInt8EnumMember BoolInt8Enum, 
    boolInt16EnumMember BoolInt16Enum, 
    boolInt32EnumMember BoolInt32Enum
} 
BusDef ::= SEQUENCE 
{ 
    busStandardTypesDefMember BusStandardTypesDef, 
    busAliasesToStandardTypesDefMember BusAliasesToStandardTypesDef, 
    busEnumsDefMember BusEnumsDef
} 
END
