INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
AliasBoolean ::= MatLab-Boolean
AliasDouble ::= MatLab-Double
AliasInt16 ::= MatLab-Int16
AliasInt32 ::= MatLab-Int32
AliasInt8 ::= MatLab-Int8
AliasSingle ::= MatLab-Single
AliasUInt16 ::= MatLab-Uint16
AliasUInt32 ::= MatLab-Uint32
AliasUInt8 ::= MatLab-Uint8
I1-Type ::= SEQUENCE (SIZE(2)) OF SEQUENCE (SIZE(2)) OF AliasDouble
I2-Type ::= SEQUENCE (SIZE(2)) OF SEQUENCE (SIZE(2)) OF AliasSingle
I3-Type ::= SEQUENCE (SIZE(2)) OF SEQUENCE (SIZE(2)) OF AliasInt8
I4-Type ::= SEQUENCE (SIZE(2)) OF SEQUENCE (SIZE(2)) OF AliasUInt8
I5-Type ::= SEQUENCE (SIZE(2)) OF SEQUENCE (SIZE(2)) OF AliasInt16
I6-Type ::= SEQUENCE (SIZE(2)) OF SEQUENCE (SIZE(2)) OF AliasUInt16
I7-Type ::= SEQUENCE (SIZE(2)) OF SEQUENCE (SIZE(2)) OF AliasInt32
I8-Type ::= SEQUENCE (SIZE(2)) OF SEQUENCE (SIZE(2)) OF AliasUInt32
I9-Type ::= SEQUENCE (SIZE(2)) OF SEQUENCE (SIZE(2)) OF AliasBoolean
O1-Type ::= SEQUENCE (SIZE(2)) OF SEQUENCE (SIZE(2)) OF AliasDouble
O2-Type ::= SEQUENCE (SIZE(2)) OF SEQUENCE (SIZE(2)) OF AliasSingle
O3-Type ::= SEQUENCE (SIZE(2)) OF SEQUENCE (SIZE(2)) OF AliasInt8
O4-Type ::= SEQUENCE (SIZE(2)) OF SEQUENCE (SIZE(2)) OF AliasUInt8
O5-Type ::= SEQUENCE (SIZE(2)) OF SEQUENCE (SIZE(2)) OF AliasInt16
O6-Type ::= SEQUENCE (SIZE(2)) OF SEQUENCE (SIZE(2)) OF AliasUInt16
O7-Type ::= SEQUENCE (SIZE(2)) OF SEQUENCE (SIZE(2)) OF AliasInt32
O8-Type ::= SEQUENCE (SIZE(2)) OF SEQUENCE (SIZE(2)) OF AliasUInt32
O9-Type ::= SEQUENCE (SIZE(2)) OF SEQUENCE (SIZE(2)) OF AliasBoolean
END
