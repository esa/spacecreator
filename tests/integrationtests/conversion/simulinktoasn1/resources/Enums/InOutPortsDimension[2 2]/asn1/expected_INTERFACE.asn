INTERFACE DEFINITIONS ::= BEGIN
IMPORTS
MatLab-Boolean FROM MATLAB-STANDARD-DATATYPES
MatLab-Double FROM MATLAB-STANDARD-DATATYPES
MatLab-Int16 FROM MATLAB-STANDARD-DATATYPES
MatLab-Int32 FROM MATLAB-STANDARD-DATATYPES
MatLab-Int8 FROM MATLAB-STANDARD-DATATYPES
MatLab-Single FROM MATLAB-STANDARD-DATATYPES
MatLab-Uint16 FROM MATLAB-STANDARD-DATATYPES
MatLab-Uint32 FROM MATLAB-STANDARD-DATATYPES
MatLab-Uint8 FROM MATLAB-STANDARD-DATATYPES
;
BoolInt16Enum ::= ENUMERATED
{
    no(-1),
    yes(1)
}
BoolInt32Enum ::= ENUMERATED
{
    no(-1),
    yes(1)
}
BoolInt8Enum ::= ENUMERATED
{
    no(-1),
    yes(1)
}
BoolSimulinkIntEnumType ::= ENUMERATED
{
    no(-1),
    yes(1)
}
BoolUInt16Enum ::= ENUMERATED
{
    no(0),
    yes(1)
}
BoolUInt8Enum ::= ENUMERATED
{
    no(0),
    yes(1)
}
I1-Type ::= SEQUENCE (SIZE(2)) OF SEQUENCE (SIZE(2)) OF BoolSimulinkIntEnumType
I2-Type ::= SEQUENCE (SIZE(2)) OF SEQUENCE (SIZE(2)) OF BoolUInt8Enum
I3-Type ::= SEQUENCE (SIZE(2)) OF SEQUENCE (SIZE(2)) OF BoolUInt16Enum
I4-Type ::= SEQUENCE (SIZE(2)) OF SEQUENCE (SIZE(2)) OF BoolInt8Enum
I5-Type ::= SEQUENCE (SIZE(2)) OF SEQUENCE (SIZE(2)) OF BoolInt16Enum
I6-Type ::= SEQUENCE (SIZE(2)) OF SEQUENCE (SIZE(2)) OF BoolInt32Enum
O1-Type ::= SEQUENCE (SIZE(2)) OF SEQUENCE (SIZE(2)) OF BoolSimulinkIntEnumType
O2-Type ::= SEQUENCE (SIZE(2)) OF SEQUENCE (SIZE(2)) OF BoolUInt8Enum
O3-Type ::= SEQUENCE (SIZE(2)) OF SEQUENCE (SIZE(2)) OF BoolUInt16Enum
O4-Type ::= SEQUENCE (SIZE(2)) OF SEQUENCE (SIZE(2)) OF BoolInt8Enum
O5-Type ::= SEQUENCE (SIZE(2)) OF SEQUENCE (SIZE(2)) OF BoolInt16Enum
O6-Type ::= SEQUENCE (SIZE(2)) OF SEQUENCE (SIZE(2)) OF BoolInt32Enum
END
